Attribute VB_Name = "Mod_Cad"
Public Sub InsertJBlock(Filename As String, TblPT As Variant, Space As String)
Dim XYZScale As Double
Dim Rotation As Double

 

  'InsertionPoint(0) = 0#: InsertionPoint(1) = 0#: InsertionPoint(2) = 0#
  XYZScale = 1#
  Rotation = 0#
 
  If Space = "Model" Then
    ThisDrawing.ModelSpace.InsertBlock TblPT, Filename, XYZScale, XYZScale, XYZScale, Rotation
   
   
Else
      ThisDrawing.PaperSpace.InsertBlock TblPT, Filename, XYZScale, XYZScale, XYZScale, Rotation
  End If
End Sub

Public Sub InsertJBlock1(Filename As String, TblPT As Variant, Space As String)
Dim XYZScale As Double
Dim Rotation As Double

 

  'InsertionPoint(0) = 0#: InsertionPoint(1) = 0#: InsertionPoint(2) = 0#
  XYZScale = 1#
  Rotation = 0#
 
  If Space = "Model" Then
    ThisDrawing.ModelSpace.InsertBlock TblPT, Filename, XYZScale, XYZScale, XYZScale, Rotation
   
   
Else
      ThisDrawing.PaperSpace.InsertBlock TblPT, Filename, XYZScale, XYZScale, XYZScale, Rotation
  End If
End Sub

Attribute VB_Name = "Mod_Code"
Public Sub ShowCode()
frmCode.show
End Sub
Public Sub writeCode(mShow As Variant)
'############################################################################
'############################################################################
'#          11/15/12 Working JIN
'#
'#
'#
'#
'#
'############################################################################
'############################################################################

Dim DB As Database
Dim RstProjCode, rstProjMuni, rstRefCode, rstBisRow, rstOCC, rstConType, rstExtElem0, rstExtElem1 As Recordset
Dim strProjCode, strProjMuni, strRefCode, strBisRow, strOCC, strConType, strExtElem0, strExtElem1 As String
Dim nRefCode, nBISrow, nOCCrow As Integer    'ProjSet no.
Dim iattr_CODE, iattr_refcode, iattr_BISrow, iattr_OCC, iattr_ConType, iattr_ExtElem0, iattr_ExtElem1 As Integer
'Dim rcArray As Variant
Dim TblPT(0 To 2) As Double
Dim tblPT2(0 To 2) As Double
'Dim tmpArrayAss(0 To 1) As Double

'Dim tblWidth As Double
Dim txtHt As Double
Dim textObj As AcadText
Dim attributeObj As AcadAttribute
'Dim height As Double
Dim mode As Long
'Dim prompt As String

Dim nCODEHeadDwg, nREFCODEDwg, nDOBHDDwg, nDOBRowDwg, nCODEBCHDDwg As Variant
Dim nJumpHead, nJumpREFCODEROW, nJumpDOBHD, nJumpBISRow As Integer
Dim blockRefObj As AcadBlockReference
Dim BlkObj As Object
Dim k, l As Integer

'frmWorkItem.ListBox1.Clear
CreateCNstyle
TblPT(0) = 0: TblPT(1) = 0: TblPT(2) = 0
tblPT2(0) = -300: tblPT2(1) = 0: tblPT2(2) = 0
txtHt = 4
txtRow = ""
mode = acAttributeModeVerify
    If mShow = False Then
        nCODEHeadDwg = "\\jwja-svr-10\drawfile\jvba\XCODE_HD01.dwg"
    Else
        nCODEHeadDwg = "\\jwja-svr-10\drawfile\jvba\XCODE_HD02.dwg" '8/25/14
    End If
    nREFCODEDwg = "\\jwja-svr-10\drawfile\jvba\XCODE_REFCODE_ROW01.dwg"
    nDOBHDDwg = "\\jwja-svr-10\drawfile\jvba\XCODE_DOB_HD01.dwg"
    nDOBRowDwg = "\\jwja-svr-10\drawfile\jvba\XCODE_BIS_ROW01.dwg"
    nCODEBCHDDwg = "\\jwja-svr-10\drawfile\jvba\XCODE_BC_HD01.dwg"
    nOCCTYPEROWDwg = "\\jwja-svr-10\drawfile\jvba\XCODE_OCC_ROW01.dwg"
    nCONTYPEHDDwg = "\\jwja-svr-10\drawfile\jvba\XCODE_CONTYPE_HD01.dwg"
    nCONTYPEROWDwg = "\\jwja-svr-10\drawfile\jvba\XCODE_CONTYPE_ROW01.dwg"
    nAHHDDwg = "\\jwja-svr-10\drawfile\jvba\XCODE_AH_HD01.dwg"
    nAHROWDwg = "\\jwja-svr-10\drawfile\jvba\XCODE_AH_ROW01.dwg"
    
    nELEMHDDwg = "\\jwja-svr-10\drawfile\jvba\XCODE_CON_ELEM_HD01.dwg"
    nELEM0Dwg = "\\jwja-svr-10\drawfile\jvba\XCODE_CON_ELEM0_ROW01.dwg"
    nELEM1Dwg = "\\jwja-svr-10\drawfile\jvba\XCODE_CON_ELEM1_ROW01.dwg"
    If mShow = False Then
    nJumpHead = 204 '17 X 12
    Else
    nJumpHead = 240 '20 X 12  '8/25/14
    End If
    nJumpREFCODEROW = 12 '1 X 12
    nJumpDOBHD = 18
    nJumpBISRow = 24 '2 X 12
    nJumpOCCTYPEHD = 42 '2 X 12
    nJumpOCCTYPEROW = 12 '2 X 12
    nJumpCONTYPEHD = 24
    nJumpCONTYPEROW = 12
    nJumpAHHD = 36
    nJumpAHROW = 12
    
    nJumpCONELEMHD = 36
    nJumpCONELEM0ROW = 12
    nJumpCONELEM1ROW = 12
    
    
    'InsertJBlock "H:\drawfile\jvba\XCODE_HD01.dwg", tblPT, "Model"

'tblPT(1) = tblPT(1) - nJumpHead

Set DB = OpenDatabase("\\jwja-svr-10\jdb\db_OUTSPEC\x-cl_org_outspec_02.mdb")
xProj_no = frmCode.seleproj
Debug.Print xAssID
strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, Project.TYPE, " _
& "Project.STATUS, Project.CID, PROJCODE.BLOCK, PROJCODE.LOT, PROJCODE.SECTION, " _
& "PROJCODE.MUNI, PROJCODE.ZONE, PROJCODE.LOTSIZE, PROJCODE.COVERAGE_EXISTING, " _
& "PROJCODE.COVERAGE_NEW, PROJCODE.COMMBD, PROJCODE.BIN, PROJCODE.STORY, PROJCODE.STORY_NW, PROJCODE.OVZONE, " _
& "PROJCODE.ZONEMAP, PROJCODE.BLDGHT_EX, PROJCODE.BLDGHT_NW, PROJCODE.AREA_EX, PROJCODE.AREA_ADD, PROJCODE.AREA_NW, PROJCODE.AREA_TOTAL, " _
& "PROJCODE.DU_EX, PROJCODE.DU_ADD, PROJCODE.DU_NW, PROJCODE.DU_TOTAL, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) LEFT JOIN Contact ON PROJCODE.MUNI = Contact.CID " _
& "WHERE (((PROJCODE.PROJ_NO)='" & xProj_no & "'));"

'strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, " _
& "Project.TYPE, Project.STATUS, Project.CID, PROJCODE.BLOCK, PROJCODE.LOT, " _
& "PROJCODE.SECTION, PROJCODE.MUNI, PROJCODE.ZONE, PROJCODE.LOTSIZE, " _
& "PROJCODE.COVERAGE_EXISTING, PROJCODE.COVERAGE_NEW, PROJCODE.COMMBD, PROJCODE.BIN, " _
& "PROJCODE.STORY, PROJCODE.OVZONE, PROJCODE.ZONEMAP, PROJCODE.BLDGHT_EX, PROJCODE.BLDGHT_NW, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) INNER JOIN Contact ON PROJCODE.MUNI = Contact.CID " _
& "WHERE (((PROJCODE.PROJ_NO)='" & xProj_no & "'));"


Set RstProjCode = DB.OpenRecordset(strProjCode)
Debug.Print "REC Count: " & RstProjCode.RecordCount
RstProjCode.MoveLast
RstProjCode.MoveFirst
If RstProjCode.RecordCount = 0 Then
    GoTo Exit_writecode
End If
With RstProjCode
    
    mprojcodeID = !projcodeid
    Set blockRefObj = ThisDrawing.ModelSpace.InsertBlock _
                 (TblPT, nCODEHeadDwg, 1, 1, 1, 0) 'First dwg
    Dim varAttributes As Variant
    varAttributes = blockRefObj.GetAttributes
    For iattr_CODE = LBound(varAttributes) To UBound(varAttributes)
        Debug.Print varAttributes(iattr_CODE).TagString
'************ PROJ_NO ***************************************************************
        If varAttributes(iattr_CODE).TagString = "XPROJ_NO" Then
            If IsNull(!PROJ_NO) = True Then
                varAttributes(iattr_CODE).textString = ""
            Else
                varAttributes(iattr_CODE).textString = !PROJ_NO
                Debug.Print varAttributes(iattr_CODE).textString
            End If
        End If
'************ DATE ***************************************************************
        If varAttributes(iattr_CODE).TagString = "XDATE" Then
                varAttributes(iattr_CODE).textString = Date
        End If
'************ XPROJADDR ***************************************************************
        If varAttributes(iattr_CODE).TagString = "XPROJADDR" Then
            If IsNull(!PROJ_ADDR) = True Then
                varAttributes(iattr_CODE).textString = ""
            Else
                varAttributes(iattr_CODE).textString = !PROJ_ADDR
                Debug.Print varAttributes(iattr_CODE).textString
            End If
        End If
'************ XBLOCK ***************************************************************
        If varAttributes(iattr_CODE).TagString = "XBLOCK" Then
            If IsNull(!Block) = True Then
                varAttributes(iattr_CODE).textString = ""
            Else
                varAttributes(iattr_CODE).textString = !Block
                Debug.Print varAttributes(iattr_CODE).textString
            End If
        End If
'************ XLOT ***************************************************************
        If varAttributes(iattr_CODE).TagString = "XLOT" Then
            If IsNull(!LOT) = True Then
                varAttributes(iattr_CODE).textString = ""
            Else
                varAttributes(iattr_CODE).textString = !LOT
                Debug.Print varAttributes(iattr_CODE).textString
            End If
        End If
'************ XBIN ***************************************************************
        If varAttributes(iattr_CODE).TagString = "XBIN" Then
            If IsNull(!BIN) = True Then
                varAttributes(iattr_CODE).textString = ""
            Else
                varAttributes(iattr_CODE).textString = !BIN
                Debug.Print varAttributes(iattr_CODE).textString
            End If
        End If
'************ XCB ***************************************************************
        If varAttributes(iattr_CODE).TagString = "XCB" Then
            If IsNull(!COMMBD) = True Then
                varAttributes(iattr_CODE).textString = ""
            Else
                varAttributes(iattr_CODE).textString = !COMMBD
                Debug.Print varAttributes(iattr_CODE).textString
            End If
        End If
'************ XHT ***************************************************************
        If varAttributes(iattr_CODE).TagString = "XHT" Then
            If IsNull(!BLDGHT_EX) = True Then
                varAttributes(iattr_CODE).textString = ""
            Else
                varAttributes(iattr_CODE).textString = !BLDGHT_EX
                Debug.Print varAttributes(iattr_CODE).textString
            End If
        End If
'+++++++++++++++++++++++++++++++++++++++++++++++++++++++++++++++++++++++++++++++++++++++++
'++++++
'++++++      START OF
'++++++      8/25/14 EDITED FOR MORE FIELDS
'++++++
'++++++
'++++++
'+++++++++++++++++++++++++++++++++++++++++++++++++++++++++++++++++++++++++++++++++++++++++




'************ XHT_NW ***************************************************************
        If varAttributes(iattr_CODE).TagString = "XHT_NW" Then
            If IsNull(!BLDGHT_NW) = True Then
                varAttributes(iattr_CODE).textString = ""
            Else
                varAttributes(iattr_CODE).textString = !BLDGHT_NW
                Debug.Print varAttributes(iattr_CODE).textString
            End If
        End If
'************ XSTORY ***************************************************************
        If varAttributes(iattr_CODE).TagString = "XSTORY" Then
            If IsNull(!STORY) = True Then
                varAttributes(iattr_CODE).textString = ""
            Else
                varAttributes(iattr_CODE).textString = !STORY
                Debug.Print varAttributes(iattr_CODE).textString
            End If
        End If
'************ XSTORY_NW ***************************************************************
        If varAttributes(iattr_CODE).TagString = "XSTORY_NW" Then
            If IsNull(!STORY_NW) = True Then
                varAttributes(iattr_CODE).textString = ""
            Else
                varAttributes(iattr_CODE).textString = !STORY_NW
                Debug.Print varAttributes(iattr_CODE).textString
            End If
        End If
'************ XDU_EX ***************************************************************
        If varAttributes(iattr_CODE).TagString = "XDU_EX" Then
            If IsNull(!DU_EX) = True Then
                varAttributes(iattr_CODE).textString = ""
            Else
                varAttributes(iattr_CODE).textString = !DU_EX
                Debug.Print varAttributes(iattr_CODE).textString
            End If
        End If
'************ XDU_ADD ***************************************************************
        If varAttributes(iattr_CODE).TagString = "XDU_ADD" Then
            If IsNull(!DU_ADD) = True Then
                varAttributes(iattr_CODE).textString = ""
            Else
                varAttributes(iattr_CODE).textString = !DU_ADD
                Debug.Print varAttributes(iattr_CODE).textString
            End If
        End If
'************ XDU_NW ***************************************************************
        If varAttributes(iattr_CODE).TagString = "XDU_NW" Then
            If IsNull(!DU_NW) = True Then
                varAttributes(iattr_CODE).textString = ""
            Else
                varAttributes(iattr_CODE).textString = !DU_NW
                Debug.Print varAttributes(iattr_CODE).textString
            End If
        End If
'************ XDU_TOT ***************************************************************
        If varAttributes(iattr_CODE).TagString = "XDU_TOT" Then
            If IsNull(!DU_TOTAL) = True Then
                varAttributes(iattr_CODE).textString = ""
            Else
                varAttributes(iattr_CODE).textString = !DU_TOTAL
                Debug.Print varAttributes(iattr_CODE).textString
            End If
        End If
'************ XAREA_EX ***************************************************************
        If varAttributes(iattr_CODE).TagString = "XAREA_EX" Then
            If IsNull(!AREA_EX) = True Then
                varAttributes(iattr_CODE).textString = ""
            Else
                varAttributes(iattr_CODE).textString = !AREA_EX
                Debug.Print varAttributes(iattr_CODE).textString
            End If
        End If
'************ XAREA_ADD ***************************************************************
        If varAttributes(iattr_CODE).TagString = "XAREA_ADD" Then
            If IsNull(!AREA_ADD) = True Then
                varAttributes(iattr_CODE).textString = ""
            Else
                varAttributes(iattr_CODE).textString = !AREA_ADD
                Debug.Print varAttributes(iattr_CODE).textString
            End If
        End If
'************ XAREA_NW ***************************************************************
        If varAttributes(iattr_CODE).TagString = "XAREA_NW" Then
            If IsNull(!AREA_NW) = True Then
                varAttributes(iattr_CODE).textString = ""
            Else
                varAttributes(iattr_CODE).textString = !AREA_NW
                Debug.Print varAttributes(iattr_CODE).textString
            End If
        End If
'************ XAREA_TOT ***************************************************************
        If varAttributes(iattr_CODE).TagString = "XAREA_TOT" Then
            If IsNull(!AREA_TOTAL) = True Then
                varAttributes(iattr_CODE).textString = ""
            Else
                varAttributes(iattr_CODE).textString = !AREA_TOTAL
                Debug.Print varAttributes(iattr_CODE).textString
            End If
        End If
'+++++++++++++++++++++++++++++++++++++++++++++++++++++++++++++++++++++++++++++++++++++++++
'++++++
'++++++      END OF
'++++++      8/25/14 EDITED FOR MORE FIELDS
'++++++
'++++++
'++++++
'+++++++++++++++++++++++++++++++++++++++++++++++++++++++++++++++++++++++++++++++++++++++++


'************ XZONE ***************************************************************
        If varAttributes(iattr_CODE).TagString = "XZONE" Then
            If IsNull(!ZONE) = True Then
                varAttributes(iattr_CODE).textString = ""
            Else
                varAttributes(iattr_CODE).textString = !ZONE
                Debug.Print varAttributes(iattr_CODE).textString
            End If
        End If
'************ XLOTSIZE ***************************************************************
        If varAttributes(iattr_CODE).TagString = "XLOTSIZE" Then
            If IsNull(!LOTSIZE) = True Then
                varAttributes(iattr_CODE).textString = ""
            Else
                varAttributes(iattr_CODE).textString = Format(!LOTSIZE, "0,0") & " S.F. APPROX."
                Debug.Print varAttributes(iattr_CODE).textString
            End If
        End If
'************ XCOVERAGE_EX ***************************************************************
        If varAttributes(iattr_CODE).TagString = "XCOVERAGE_EX" Then
            If IsNull(!COVERAGE_EXISTING) = True Then
                varAttributes(iattr_CODE).textString = ""
            Else
                varAttributes(iattr_CODE).textString = !COVERAGE_EXISTING
                Debug.Print varAttributes(iattr_CODE).textString
            End If
        End If
'************ XCOVERAGE_NW ***************************************************************
        If varAttributes(iattr_CODE).TagString = "XCOVERAGE_NW" Then
            If IsNull(!COVERAGE_NEW) = True Then
                varAttributes(iattr_CODE).textString = ""
            Else
                varAttributes(iattr_CODE).textString = !COVERAGE_NEW
                Debug.Print varAttributes(iattr_CODE).textString
            End If
        End If
'************ XOVZONE ***************************************************************
        If varAttributes(iattr_CODE).TagString = "XOVZONE" Then
            If IsNull(!OVZONE) = True Then
                varAttributes(iattr_CODE).textString = ""
            Else
                varAttributes(iattr_CODE).textString = !OVZONE
                Debug.Print varAttributes(iattr_CODE).textString
            End If
        End If
'************ XMAP ***************************************************************
        If varAttributes(iattr_CODE).TagString = "XMAP" Then
            If IsNull(!ZONEMAP) = True Then
                varAttributes(iattr_CODE).textString = ""
            Else
                varAttributes(iattr_CODE).textString = !ZONEMAP
                Debug.Print varAttributes(iattr_CODE).textString
            End If
        End If
        
'************ XMUNI ***************************************************************
        If varAttributes(iattr_CODE).TagString = "XMUNI" Then
            If IsNull(!MUNI) = True Then
                varAttributes(iattr_CODE).textString = ""
            Else
                varAttributes(iattr_CODE).textString = !COMPANY
                Debug.Print varAttributes(iattr_CODE).textString
            End If
        End If
        If varAttributes(iattr_CODE).TagString = "XMUNISTREET" Then
            Debug.Print "+++++++++++++++++ Got XMUNIstreet ++++++" & varAttributes(iattr_MUNI).TagString
            If IsNull(!STREET) = True Then
                varAttributes(iattr_CODE).textString = ""
            Else
                varAttributes(iattr_CODE).textString = !STREET
                Debug.Print varAttributes(iattr_CODE).textString
            End If
        End If
        If varAttributes(iattr_CODE).TagString = "XMUNICSZ" Then
            If IsNull(!csz) = True Then
                varAttributes(iattr_CODE).textString = ""
            Else
                varAttributes(iattr_CODE).textString = !csz
                Debug.Print varAttributes(iattr_CODE).textString
            End If
        End If
        ''End With
    Next iattr_CODE
    TblPT(1) = TblPT(1) - nJumpHead
End With
RstProjCode.Close
'**********************************************************************************
'*    CODE routine
'**********************************************************************************
    
    strRefCode = "SELECT PROJCODE.PROJCODEID, CODE.CODENAME " _
    & "FROM CODE INNER JOIN (PROJCODE INNER JOIN CONNCODE ON " _
    & "PROJCODE.PROJCODEID = CONNCODE.PROJCODEID) ON CODE.CODEID = CONNCODE.CODEID " _
    & "WHERE (((PROJCODE.PROJCODEID)=" & mprojcodeID & "))"
     Set rstRefCode = DB.OpenRecordset(strRefCode)
     With rstRefCode
    nRefCode = rstRefCode.RecordCount
    .MoveLast
    .MoveFirst
nRefCode = rstRefCode.RecordCount
     For k = 1 To nRefCode
        Set blockRefObj = ThisDrawing.ModelSpace.InsertBlock _
                                     (TblPT, nREFCODEDwg, 1, 1, 1, 0)
        Dim varAttributes2 As Variant
        varAttributes2 = blockRefObj.GetAttributes
        For iattr_refcode = LBound(varAttributes2) To UBound(varAttributes2)
        
            If varAttributes2(iattr_refcode).TagString = "XCODENAME" Then
                If IsNull(!CODENAME) = True Then
                    varAttributes2(iattr_refcode).textString = ""
                Else
                    varAttributes2(iattr_refcode).textString = !CODENAME
                    Debug.Print varAttributes(iattr_refcode).textString
                End If
            End If
        
        Next iattr_refcode
        'rstRefCode.Close
        TblPT(1) = TblPT(1) - nJumpREFCODEROW
        Debug.Print "K:" & k
    .MoveNext
    Next k
    End With
    rstRefCode.Close
    Set blockRefObj = ThisDrawing.ModelSpace.InsertBlock _
                    (TblPT, nDOBHDDwg, 1, 1, 1, 0)
    TblPT(1) = TblPT(1) - nJumpDOBHD
'**********************************************************************************
'**********************************************************************************
'*    BIS routine
'**********************************************************************************
    
    strBisRow = "SELECT PROJCODE.PROJCODEID, proj_dob.bis, proj_dob.projbisnote, " _
    & "proj_dob.dobjobid, proj_dob.projbistype " _
    & "FROM PROJCODE INNER JOIN proj_dob ON PROJCODE.PROJCODEID = proj_dob.projcodeid " _
    & "WHERE (((PROJCODE.PROJCODEID)=" & mprojcodeID & "))"

     Set rstBisRow = DB.OpenRecordset(strBisRow)
     If rstBisRow.RecordCount = 0 Then
     GoTo SKIP_BISROUTINE
     
     End If
     
     With rstBisRow
     .MoveLast
     .MoveFirst
     nBISrow = rstBisRow.RecordCount
     For l = 0 To nBISrow - 1
        Set blockRefObj = ThisDrawing.ModelSpace.InsertBlock _
                                     (TblPT, nDOBRowDwg, 1, 1, 1, 0)
        Dim varAttributes3 As Variant
        varAttributes3 = blockRefObj.GetAttributes
        For iattr_BISrow = LBound(varAttributes3) To UBound(varAttributes3)
'************ XBO ***************************************************************
            'If varAttributes3(iattr_BISrow).TagString = "XBO" Then
                'If IsNull(!bisorder) = True Then '++++++++++++++++++++++++++++++++++++++++++
                    'varAttributes3(iattr_BISrow).TextString = ""
                'Else
                    'varAttributes3(iattr_BISrow).TextString = !bisorder
                    
                'End If
            'End If
'************ XBIS ***************************************************************
            If varAttributes3(iattr_BISrow).TagString = "XBIS" Then
                If IsNull(!bis) = True Then
                    varAttributes3(iattr_BISrow).textString = ""
                Else
                    varAttributes3(iattr_BISrow).textString = !bis
                    
                End If
            End If
'************ XBISTYPE ***************************************************************
            If varAttributes3(iattr_BISrow).TagString = "XBISTYPE" Then
                If IsNull(!projbistype) = True Then
                    varAttributes3(iattr_BISrow).textString = ""
                Else
                    varAttributes3(iattr_BISrow).textString = !projbistype
                    
                End If
            End If
'************ XBISDESC1 ***************************************************************
            If varAttributes3(iattr_BISrow).TagString = "XBISDESC1" Then
                If IsNull(!projbisnote) = True Then '++++++++++++++++++++++++++++++++++++++++++
                    varAttributes3(iattr_BISrow).textString = ""
                Else
                    varAttributes3(iattr_BISrow).textString = SEPTEXT2(!projbisnote, 1, 3, 33)
                    
                End If
            End If
'************ XBISDESC2 ***************************************************************
            If varAttributes3(iattr_BISrow).TagString = "XBISDESC2" Then
                If IsNull(!projbisnote) = True Then '++++++++++++++++++++++++++++++++++++++++++
                    varAttributes3(iattr_BISrow).textString = ""
                Else
                    varAttributes3(iattr_BISrow).textString = SEPTEXT2(!projbisnote, 2, 3, 33)
                    
                End If
            End If
'************ XBISDESC1 ***************************************************************
            If varAttributes3(iattr_BISrow).TagString = "XBISDESC2" Then
                If IsNull(!projbisnote) = True Then '++++++++++++++++++++++++++++++++++++++++++
                    varAttributes3(iattr_BISrow).textString = ""
                Else
                    varAttributes3(iattr_BISrow).textString = SEPTEXT2(!projbisnote, 3, 3, 33)
                    
                End If
            End If



'************ XBO ***************************************************************
        Next iattr_BISrow
        
        TblPT(1) = TblPT(1) - nJumpBISRow
    .MoveNext
    Next l
    rstBisRow.Close
    End With
SKIP_BISROUTINE:
'**********************************************************************************
'**********************************************************************************
'*    UG/OCC routine
'**********************************************************************************
'**********************************************************************************
    
Set blockRefObj = ThisDrawing.ModelSpace.InsertBlock _
                                     (TblPT, nCODEBCHDDwg, 1, 1, 1, 0)
   TblPT(1) = TblPT(1) - nJumpOCCTYPEHD
'**********************************************************************************
    'strOCC = "SELECT CONNUSEGP.PROJCODEID, CONNUSEGP.PROJUSEGPNOTE, USEGP.USEGP, USEGP.USEGPNAME, USEGP.USEGPDESC " _
& "FROM USEGP INNER JOIN (PROJCODE INNER JOIN CONNUSEGP ON PROJCODE.PROJCODEID = CONNUSEGP.PROJCODEID) ON USEGP.USEGPID = CONNUSEGP.USEGPID " _
& "WHERE (((CONNUSEGP.PROJCODEID)=" & MPROJCODEID & "));"
strOCC = "SELECT CONNOCCGRP.CONNOCCGRPID, CONNOCCGRP.OCCGRPID, CONNOCCGRP.PROJCODEID, " _
& "CONNOCCGRP.PROJOCCGRPNOTE, OCCGRP.OCCGRP, OCCGRP.OCCGRPNAME, CONNOCCGRP.PROJ_OCCLOADTYPE, " _
& "CONNOCCGRP.PROJ_OCCLOAD, CONNOCCGRP.PROJ_OCCLOADUNIT, CONNOCCGRP.ProjOccLoadNote " _
& "FROM OCCGRP INNER JOIN CONNOCCGRP ON OCCGRP.OCCGRPID = CONNOCCGRP.OCCGRPID " _
& "WHERE (((CONNOCCGRP.PROJCODEID)=" & mprojcodeID & "));"

     Set rstOCC = DB.OpenRecordset(strOCC)
     With rstOCC
     .MoveLast
    .MoveFirst
     Do While Not rstOCC.EOF
         nOCCrow = rstOCC.RecordCount
        .MoveLast
        .MoveFirst
        If rstOCC.RecordCount = 0 Then
            GoTo NoOCCStep
        End If
        
         For m = 1 To nOCCrow
            Set blockRefObj = ThisDrawing.ModelSpace.InsertBlock _
                                         (TblPT, nOCCTYPEROWDwg, 1, 1, 1, 0)
            Dim varAttributes4 As Variant
            varAttributes4 = blockRefObj.GetAttributes
            For iattr_OCC = LBound(varAttributes4) To UBound(varAttributes4)
    '************ XOCCTYPE ***************************************************************
                If varAttributes4(iattr_OCC).TagString = "XOCCTYPE" Then
                    If IsNull(!OCCGRP) = True Then '++++++++++++++++++++++++++++++++++++++++++
                        varAttributes4(iattr_OCC).textString = ""
                    Else
                        varAttributes4(iattr_OCC).textString = !OCCGRP
                        
                    End If
                End If
    '************ XOCCNAME ***************************************************************
                If varAttributes4(iattr_OCC).TagString = "XOCCNAME" Then
                    If IsNull(!OCCGRPNAME) = True Then
                        varAttributes4(iattr_OCC).textString = ""
                    Else
                        varAttributes4(iattr_OCC).textString = !OCCGRPNAME
                        
                    End If
                End If
    '************ XOCCRATE ***************************************************************
                If varAttributes4(iattr_OCC).TagString = "XOCCRATE" Then
                    If IsNull(!PROJ_OCCLOAD) = True Then
                        varAttributes4(iattr_OCC).textString = ""
                    Else
                        varAttributes4(iattr_OCC).textString = !PROJ_OCCLOAD
                        
                    End If
                End If
    '************ XOCCNOTE ***************************************************************
                If varAttributes4(iattr_OCC).TagString = "XOCCNOTE" Then
                    If IsNull(!PROJOCCGRPNOTE) = True Then
                        varAttributes4(iattr_OCC).textString = ""
                    Else
                        varAttributes4(iattr_OCC).textString = !PROJOCCGRPNOTE
                        
                    End If
                End If
    '************  ***************************************************************
            Next iattr_OCC
            
            TblPT(1) = TblPT(1) - nJumpOCCTYPEROW
        .MoveNext
        Next m
    Loop
    End With
'**********************************************************************************
'**********************************************************************************
'*    CONTYPE routine
'**********************************************************************************
'**********************************************************************************


strConType = "SELECT CONNCONTYPE.CONNCONTYPEID, CONNCONTYPE.CONTYPEID, " _
& "CONNCONTYPE.PROJCODEID, CONNCONTYPE.ProjCONTYPEnote, CONTYPE.CONTYPE, CONTYPE.CONTYPEDESC " _
& "FROM CONTYPE INNER JOIN CONNCONTYPE ON CONTYPE.CONTYPEID = CONNCONTYPE.CONTYPEID " _
& "WHERE (((CONNCONTYPE.PROJCODEID)=" & mprojcodeID & "));"


Set rstConType = DB.OpenRecordset(strConType)
With rstConType
    .MoveLast
    .MoveFirst
     Do While Not rstConType.EOF
       nCONTYPErow = rstConType.RecordCount
        Debug.Print nCONTYPErow
        If nCONTYPErow > 0 Then
            Set blockRefObj = ThisDrawing.ModelSpace.InsertBlock _
                                              (TblPT, nCONTYPEHDDwg, 1, 1, 1, 0)
            TblPT(1) = TblPT(1) - nJumpCONTYPEHD
         
         End If
         
        .MoveLast
        .MoveFirst
        If rstConType.RecordCount = 0 Then
            GoTo NoCONTYPEStep
        End If
    '*************************************************************************************
    '************ 08282014 ***************************************************************
    '*************************************************************************************
        mCONNCONTYPEID = !CONNCONTYPEID
        MCONTYPEID = !CONTYPEID
    '-------------------------------------------------------------------------------------
    '-------------------------------------------------------------------------------------
        For O = 1 To nCONTYPErow
         
            Set blockRefObj = ThisDrawing.ModelSpace.InsertBlock _
                                         (TblPT, nCONTYPEROWDwg, 1, 1, 1, 0)
            Dim varAttributes5 As Variant
            varAttributes5 = blockRefObj.GetAttributes
            For iattr_ConType = LBound(varAttributes5) To UBound(varAttributes5)
                'mCONNCONTYPEID = CONNCONTYPEID
    '************ XOCCTYPE ***************************************************************
                If varAttributes5(iattr_ConType).TagString = "XCONTYPE" Then
                    If IsNull(!CONTYPE) = True Then '++++++++++++++++++++++++++++++++++++++++++
                        varAttributes5(iattr_ConType).textString = ""
                    Else
                        varAttributes5(iattr_ConType).textString = !CONTYPE
                        
                    End If
                End If
    '************ XOCCNAME ***************************************************************
                If varAttributes5(iattr_ConType).TagString = "XCONDESC" Then
                    If IsNull(!CONTYPEDESC) = True Then
                        varAttributes5(iattr_ConType).textString = ""
                    Else
                        varAttributes5(iattr_ConType).textString = !CONTYPEDESC
                        
                    End If
                End If
    '************ XOCCRATE ***************************************************************
                If varAttributes5(iattr_ConType).TagString = "XCONTYPENOTE" Then
                    If IsNull(!ProjCONTYPEnote) = True Then
                        varAttributes5(iattr_ConType).textString = ""
                    Else
                        varAttributes5(iattr_ConType).textString = !ProjCONTYPEnote
                        
                    End If
                 End If
    '+++++++++++++++++++++++++++++++++++++++++++++++++++++++++++++++++++++++++++++++++++++
    
            Next iattr_ConType
            
            TblPT(1) = TblPT(1) - nJumpOCCTYPEROW
                '###########################################################################
                '***************************************************************************
                '*   AREA/HT SUB ROUTINE
                '***************************************************************************
             If mCONNCONTYPEID <> "" Then
                'strAH = "SELECT CONNAREASTORY.CONNAREASTORYID, CONNAREASTORY.AREASTORYID, " _
                & "CONNAREASTORY.PROJCODEID, CONNAREASTORY.PROJAREASTORYNOTE, CONNAREASTORY.PROJADJAREA, " _
                & "CONNAREASTORY.PROJADJHT, AREASTORY.CONTYPE, AREASTORY.USEGPID, AREASTORY.HTFT, " _
                & "AREASTORY.STORY, AREASTORY.AREA, CONNAREASTORY.CONNCONTYPEID, USEGP.USEGP " _
                & "FROM (AREASTORY INNER JOIN CONNAREASTORY ON AREASTORY.ID = CONNAREASTORY.AREASTORYID) INNER JOIN USEGP ON AREASTORY.USEGPID = USEGP.USEGPID " _
                & "WHERE (((CONNAREASTORY.CONNCONTYPEID)=" & mCONNCONTYPEID & "));"
                
                'strAH = "SELECT CONNCONTYPE.CONNCONTYPEID,  OCCGRP.OCCGRP, CONNCONTYPE.CONTYPEID, CONNCONTYPE.PROJCODEID, CONNCONTYPE.ProjCONTYPEnote, CONNAREASTORY.PROJAREASTORYNOTE, " _
                & "CONNAREASTORY.PROJADJAREA, CONNAREASTORY.PROJADJHT, CONNAREASTORY.PROJADJSTORY, CONTYPE.CONTYPE, AREASTORY.HTFT, AREASTORY.STORY, AREASTORY.AREA " _
                & "FROM AREASTORY INNER JOIN ((CONTYPE INNER JOIN CONNCONTYPE ON CONTYPE.CONTYPEID = CONNCONTYPE.CONTYPEID) INNER JOIN CONNAREASTORY ON CONNCONTYPE.CONNCONTYPEID = CONNAREASTORY.CONNCONTYPEID) " _
                & "ON AREASTORY.ID = CONNAREASTORY.AREASTORYID " _
                & "WHERE (((CONNCONTYPE.CONNCONTYPEID)=" & mCONNCONTYPEID & "));"

                StrAH = "SELECT CONNCONTYPE.CONNCONTYPEID, OCCGRP.OCCGRP, CONNCONTYPE.CONTYPEID, CONNCONTYPE.PROJCODEID, CONNCONTYPE.ProjCONTYPEnote, CONNAREASTORY.PROJAREASTORYNOTE, " _
                & "CONNAREASTORY.PROJADJAREA, CONNAREASTORY.PROJADJHT, CONNAREASTORY.PROJADJSTORY, CONTYPE.CONTYPE, AREASTORY.HTFT, AREASTORY.STORY, AREASTORY.AREA " _
                & "FROM (CONTYPE INNER JOIN (AREASTORY INNER JOIN (CONNCONTYPE INNER JOIN CONNAREASTORY ON CONNCONTYPE.CONNCONTYPEID = CONNAREASTORY.CONNCONTYPEID) ON AREASTORY.ID = CONNAREASTORY.AREASTORYID) " _
                & "ON CONTYPE.CONTYPEID = CONNCONTYPE.CONTYPEID) INNER JOIN OCCGRP ON AREASTORY.occgrpID = OCCGRP.OCCGRPID " _
                & "WHERE (((CONNCONTYPE.projcodeID)=" & mprojcodeID & "));"
                
                '& "WHERE (((CONNCONTYPE.contypeID)=" & mcontypeID & "));"
                Set rstAH = DB.OpenRecordset(StrAH)
                With rstAH
                    .MoveLast
                    .MoveFirst
                     Do While Not rstAH.EOF
                        nAHrow = rstAH.RecordCount
                        If nAHrow > 0 Then
                            Set blockRefObj = ThisDrawing.ModelSpace.InsertBlock _
                                                              (TblPT, nAHHDDwg, 1, 1, 1, 0)
                            TblPT(1) = TblPT(1) - nJumpAHHD
                         
                         End If
                         
                        .MoveLast
                        .MoveFirst
                        If rstAH.RecordCount = 0 Then
                            GoTo NoAHStep
                        End If
                        
                         For P = 1 To nAHrow
                            Set blockRefObj = ThisDrawing.ModelSpace.InsertBlock _
                                                         (TblPT, nAHROWDwg, 1, 1, 1, 0)
                            Dim varAttributes6 As Variant
                            varAttributes6 = blockRefObj.GetAttributes
                            For iattr_AH = LBound(varAttributes6) To UBound(varAttributes6)
                    '************ XOCCTYPE ***************************************************************
                                If varAttributes6(iattr_AH).TagString = "XOCCTYPE" Then
                                    If IsNull(!OCCGRP) = True Then '++++++++++++++++++++++++++++++++++++++++++
                                        varAttributes6(iattr_AH).textString = ""
                                    Else
                                        varAttributes6(iattr_AH).textString = !OCCGRP
                                        
                                    End If
                                End If
                    '************ XAHHT ***************************************************************
                                If varAttributes6(iattr_AH).TagString = "XAHHT" Then
                                    If IsNull(!HTFT) = True Then
                                        varAttributes6(iattr_AH).textString = ""
                                    Else
                                        varAttributes6(iattr_AH).textString = !HTFT
                                        
                                    End If
                                End If
                    '************ XAHS ***************************************************************
                                If varAttributes6(iattr_AH).TagString = "XAHS" Then
                                    If IsNull(!STORY) = True Then
                                        varAttributes6(iattr_AH).textString = ""
                                    Else
                                        varAttributes6(iattr_AH).textString = !STORY
                                        
                                    End If
                                 End If
                    '************ XAHA ***************************************************************
                                If varAttributes6(iattr_AH).TagString = "XAHA" Then
                                    If IsNull(!Area) = True Then
                                        varAttributes6(iattr_AH).textString = ""
                                    Else
                                        varAttributes6(iattr_AH).textString = Format(!Area, "0,0") & " SF"
                                        
                                    End If
                                 End If
                    '************ XAHPHT ***************************************************************
                                If varAttributes6(iattr_AH).TagString = "XAHPHT" Then
                                    If IsNull(!PROJADJHT) = True Then
                                        varAttributes6(iattr_AH).textString = ""
                                    Else
                                        varAttributes6(iattr_AH).textString = !PROJADJHT
                                        
                                    End If
                                 End If
                    '************ XAHPS ***************************************************************
                                If varAttributes6(iattr_AH).TagString = "XAHPS" Then
                                    If IsNull(!PROJADJSTORY) = True Then
                                        varAttributes6(iattr_AH).textString = ""
                                    Else
                                        varAttributes6(iattr_AH).textString = !PROJADJSTORY
                                        
                                    End If
                                 End If
                    '************ XAHPA ***************************************************************
                                If varAttributes6(iattr_AH).TagString = "XAHPA" Then
                                    If IsNull(!PROJADJAREA) = True Then
                                        varAttributes6(iattr_AH).textString = ""
                                    Else
                                        varAttributes6(iattr_AH).textString = Format(!PROJADJAREA, "0,0") & " SF"
                                        
                                    End If
                                 End If
                    '************ XAHNOTE ***************************************************************
                                If varAttributes6(iattr_AH).TagString = "XAHNOTE" Then
                                    If IsNull(!PROJAREASTORYNOTE) = True Then
                                        varAttributes6(iattr_AH).textString = ""
                                    Else
                                        varAttributes6(iattr_AH).textString = !PROJAREASTORYNOTE
                                        
                                    End If
                                 End If

                    '************************************************************************************
                           Next iattr_AH
                            TblPT(1) = TblPT(1) - nJumpAHROW

                           .MoveNext
                        Next P
                    Loop
                End With
                rstAH.Close
                End If
                '###########################################################################
                '*   END AREA/HT SUB ROUTINE
                '###########################################################################
                
    '+++++++++++++++++++++++++++++++++++++++++++++++++++++++++++++++++++++++++++++++++++++
        .MoveNext
        Next O
    Loop
End With

'**********************************************************************************
'**********************************************************************************
'*    CONELEM routine
'**********************************************************************************
'**********************************************************************************
                
'+++++++++++++++++++++++++++++++++++++++++++++++++++++++++++++++++++++++++++
'+++++
'+++++ START OF CONELEM
'+++++
'+++++++++++++++++++++++++++++++++++++++++++++++++++++++++++++++++++++++++++
'iattr_ConType, iattr_ExtElem0, iattr_ExtElem1

With rstConType 'with 1
    .MoveLast
    .MoveFirst
    Do While Not rstConType.EOF
    nCONTYPErow = rstConType.RecordCount
    'For s = 1 To nCONTYPErow
    If MCONTYPEID <> "" Then 'IF 0825
        Set blockRefObj = ThisDrawing.ModelSpace.InsertBlock _
                                          (TblPT, nELEMHDDwg, 1, 1, 1, 0)
        TblPT(1) = TblPT(1) - nJumpCONELEMHD 'nJumpCONELEMHD
        'tblPT(1) = tblPT(1) - 36
        Dim varAttributes7 As Variant
        varAttributes7 = blockRefObj.GetAttributes
        
        '01###########################################################################
        For iattr_CONELEMHD = LBound(varAttributes7) To UBound(varAttributes7) 'Loop 01
            
            '************ XCONTYPE ***************************************************************
            If varAttributes7(iattr_CONELEMHD).TagString = "XCONTYPE" Then
                If IsNull(!CONTYPE) = True Then '++++++++++++++++++++++++++++++++++++++++++
                    varAttributes7(iattr_CONELEMHD).textString = ""
                Else
                    varAttributes7(iattr_CONELEMHD).textString = !CONTYPE
                    
                End If
            End If
            '************ XCONDESC ***************************************************************
            If varAttributes7(iattr_CONELEMHD).TagString = "XCONDESC" Then
                If IsNull(!CONTYPEDESC) = True Then '++++++++++++++++++++++++++++++++++++++++++
                    varAttributes7(iattr_CONELEMHD).textString = ""
                Else
                    varAttributes7(iattr_CONELEMHD).textString = !CONTYPEDESC
                    
                End If
            End If
        Next iattr_CONELEMHD
            'nELEMHDDwg = "H:\drawfile\jvba\XCODE_CON_ELEM_HD01.dwg"
            'nELEM0Dwg = "H:\drawfile\jvba\XCODE_CON_ELEM0_ROW01.dwg"
            'nELEM1Dwg = "H:\drawfile\jvba\XCODE_CON_ELEM1_ROW01.dwg"
            'nJumpCONELEMHD = 36
            'nJumpCONELEM0ROW = 12
            'nJumpCONELEM1ROW = 12
            'strExtElem0 = "SELECT EXTELEM0.EXTELEM0ID, EXTELEM0.EXTELM0, EXTELEM0.EXTELM0LEVEL, " _
            & "EXTELEM0.EXTELEM0RATE, EXTELEM0.EXTELEM0DESC, EXTELEM0.CONTYPEID FROM EXTELEM0;"
            strExtElem0 = "SELECT EXTELEM0.EXTELEM0ID, EXTELEM0.EXTELM0, EXTELEM0.EXTELM0LEVEL, " _
            & "EXTELEM0.EXTELEM0RATE, EXTELEM0.EXTELEM0DESC, CONTYPE.CONTYPEID " _
            & "FROM EXTELEM0 INNER JOIN CONTYPE ON EXTELEM0.CONTYPEID = CONTYPE.CONTYPEID " _
            & "WHERE (((CONTYPE.CONTYPEID) =" & MCONTYPEID & "))" _
            & "ORDER BY EXTELEM0.EXTELM0LEVEL;"
            '###########################################################################
            Set rstExtElem0 = DB.OpenRecordset(strExtElem0)
            
            If rstExtElem0.RecordCount > 0 Then 'If 1.5
            With rstExtElem0 'with 2
                .MoveLast
                .MoveFirst
                nExtElem0row = rstExtElem0.RecordCount
                '02###########################################################################
                Do While Not rstExtElem0.EOF
                    'nExtElem0row = rstExtElem0.RecordCount
                    If nExtElem0row > 0 Then
                        'Set blockRefObj = ThisDrawing.ModelSpace.InsertBlock _
                                                          (tblPT, nELEM0Dwg, 1, 1, 1, 0)
                        'tblPT(1) = tblPT(1) - nJumpCONELEM0ROW
                        
                     End If
                     
                    .MoveLast
                    .MoveFirst
                    If rstExtElem0.RecordCount = 0 Then
                        GoTo NoExtElem0Step
                    End If
                        '03###########################################################################
                        For Q = 1 To nExtElem0row
                        Debug.Print "Q:" & Q
                            Set blockRefObj = ThisDrawing.ModelSpace.InsertBlock _
                                                        (TblPT, nELEM0Dwg, 1, 1, 1, 0)
                            Dim varAttributes8 As Variant
                            mExtElem0ID = !EXTELEM0ID
                            varAttributes8 = blockRefObj.GetAttributes
                            '04###########################################################################
                            For iattr_ExtElem0 = LBound(varAttributes8) To UBound(varAttributes8)
                                
                                '************ XELEM0 ***************************************************************
                                If varAttributes8(iattr_ExtElem0).TagString = "XELEM0" Then
                                    If IsNull(!EXTELM0) = True Then '++++++++++++++++++++++++++++++++++++++++++
                                        varAttributes8(iattr_ExtElem0).textString = ""
                                    Else
                                        Debug.Print "stop:>>>>>" & !EXTELM0
                                        varAttributes8(iattr_ExtElem0).textString = !EXTELM0
                                        If !EXTELM0 = "INTERIOR ELEMENTS" Then
                                        Debug.Print "stop:>>>>>>>>>>>>>>>>>>>>>>>>>>>>>>>>>>" & !EXTELM0
                                        End If
                                    End If
                                End If
                                '************ XELEM0 ***************************************************************
                                If varAttributes8(iattr_ExtElem0).TagString = "XELEM0NOTE" Then
                                    If IsNull(!EXTELEM0DESC) = True Then '++++++++++++++++++++++++++++++++++++++++++
                                        varAttributes8(iattr_ExtElem0).textString = ""
                                    Else
                                        varAttributes8(iattr_ExtElem0).textString = !EXTELEM0DESC
                                        
                                    End If
                                End If
                            
                            
                            Next iattr_ExtElem0
                            TblPT(1) = TblPT(1) - nJumpCONELEM0ROW
                       
                            strExtElem1 = "SELECT EXTELEM0.EXTELEM0ID, EXTELEM1.EXTELEM1ID, EXTELEM1.EXTELEM1, EXTELEM1.EXTELEM1LEVEL, " _
                            & "EXTELEM1.EXTELEM1RATEID, EXTELEM1.EXTELEM1DESC, FIRERATE.FIRERATE " _
                            & "FROM FIRERATE INNER JOIN (EXTELEM0 INNER JOIN EXTELEM1 ON EXTELEM0.EXTELEM0ID = EXTELEM1.EXTELEM0ID) ON FIRERATE.FIRERATEID = EXTELEM1.EXTELEM1RATEID " _
                            & "WHERE (((EXTELEM0.EXTELEM0ID) = " & mExtElem0ID & "))" _
                            & "ORDER BY EXTELEM1.EXTELEM1LEVEL;"
    
    
    
    'SELECT EXTELEM0.EXTELEM0ID, EXTELEM1.EXTELEM1ID, EXTELEM1.EXTELEM1, EXTELEM1.EXTELEM1LEVEL, EXTELEM1.EXTELEM1RATEID, EXTELEM1.EXTELEM1DESC, FIRERATE.FIRERATE
    'FROM FIRERATE INNER JOIN (EXTELEM0 INNER JOIN EXTELEM1 ON EXTELEM0.EXTELEM0ID = EXTELEM1.EXTELEM0ID) ON FIRERATE.FIRERATEID = EXTELEM1.EXTELEM1RATEID
    'WHERE (((EXTELEM0.EXTELEM0ID) = 58))
    'ORDER BY EXTELEM1.EXTELEM1LEVEL;
    
    
                            '###########################################################################
                            Set rstExtElem1 = DB.OpenRecordset(strExtElem1)
                                With rstExtElem1 'with 3
                                    .MoveLast
                                    .MoveFirst
                                    '05###########################################################################
                                     'Do While Not rstExtElem1.EOF
                                        nExtElem1row = rstExtElem1.RecordCount
                                        Debug.Print nExtElem1row
                                        If nExtElem1row > 0 Then
                                            'Set blockRefObj = ThisDrawing.ModelSpace.InsertBlock _
                                                                              (tblPT, nELEM0Dwg, 1, 1, 1, 0)
                                            'tblPT(1) = tblPT(1) - nJumpCONELEM1ROW
                                            
                                         End If
                                         
                                        .MoveLast
                                        .MoveFirst
                                        If rstExtElem1.RecordCount = 0 Then
                                            GoTo NoExtElem1Step
                                        End If
                                            '06###########################################################################
                                            For R = 1 To nExtElem1row
                                                Set blockRefObj = ThisDrawing.ModelSpace.InsertBlock _
                                                                            (TblPT, nELEM1Dwg, 1, 1, 1, 0)
                                                Dim varAttributes9 As Variant
                                                varAttributes9 = blockRefObj.GetAttributes
                                                '07###########################################################################
                                                mExtElem1ID = !extelem1id
                                                For iattr_ExtElem1 = LBound(varAttributes9) To UBound(varAttributes9)
                                                    
                                                    '************ XELEM1 ***************************************************************
                                                    If varAttributes9(iattr_ExtElem1).TagString = "XELEM1" Then
                                                        If IsNull(!EXTELeM1) = True Then '++++++++++++++++++++++++++++++++++++++++++
                                                            varAttributes9(iattr_ExtElem1).textString = ""
                                                        Else
                                                            varAttributes9(iattr_ExtElem1).textString = !EXTELeM1
                                                            
                                                        End If
                                                    End If
                                                    '************ XELEM1RATE ***************************************************************
                                                    If varAttributes9(iattr_ExtElem1).TagString = "XELEM1RATE" Then
                                                        If IsNull(!FIRERATE) = True Then '++++++++++++++++++++++++++++++++++++++++++
                                                            varAttributes9(iattr_ExtElem1).textString = ""
                                                        Else
                                                            varAttributes9(iattr_ExtElem1).textString = !FIRERATE
                                                            
                                                        End If
                                                    End If
                                                    '************ XELEM1NOTE ***************************************************************
                                                    If varAttributes9(iattr_ExtElem1).TagString = "XELEM1NOTE" Then
                                                        If IsNull(!EXTELEM1DESC) = True Then '++++++++++++++++++++++++++++++++++++++++++
                                                            varAttributes9(iattr_ExtElem1).textString = ""
                                                        Else
                                                            varAttributes9(iattr_ExtElem1).textString = !EXTELEM1DESC
                                                            
                                                        End If
                                                    End If
                                                Next iattr_ExtElem1
                                                    TblPT(1) = TblPT(1) - nJumpCONELEM1ROW
                                                    .MoveNext
                                            Next R
    
                                    'Loop
                                End With 'with 3
                            'Next iattr_ExtElem0
                            'tblPT(1) = tblPT(1) - nJumpCONELEM0ROW
                            .MoveNext
                            '04###########################################################################
                        Next Q
                        '03###########################################################################
                        '.MoveNext
                Loop
                '02###########################################################################
            End With 'with 2
            End If 'if 1.5
    '###########################################################################
        'Next iattr_CONELEMHD     'LOOP1
            'tblPT(1) = tblPT(1) - nJumpCONTYPEHD
        .MoveNext
        '01###########################################################################
        
    End If 'IF 0825
    '.MoveNext

'Next s
Loop
End With 'with1

'**********************************************************************************
'**********************************************************************************
'*    CONTYPE_ELEM routine
'**********************************************************************************
'**********************************************************************************
'+++++++++++++++++++++++++++++++++++++++++++++++++++++++++++++++++++++++++++
'+++++
'+++++ END OF CONELEM
'+++++
'+++++++++++++++++++++++++++++++++++++++++++++++++++++++++++++++++++++++++++





'**********************************************************************************
NoOCCStep:
    rstOCC.Close
'rstProjCode.Close
NoAHStep:
    'rstAH.Close
NoExtElem0Step:

NoExtElem1Step:

NoCONTYPEStep:
    rstConType.Close

Set DB = Nothing

Exit_writecode:
frmCode.Hide
End Sub
'############################################################################
'############################################################################
'############################################################################
'############################################################################
'############################################################################
'############################################################################
'############################################################################
'############################################################################
'############################################################################
'############################################################################
'############################################################################
'############################################################################
'############################################################################
'############################################################################
'############################################################################
'############################################################################
'############################################################################
'############################################################################
'############################################################################
'############################################################################


Public Sub writeCode_BACKUP()
'############################################################################
'############################################################################
'#          11/15/12 Working JIN
'#
'#
'#
'#
'#
'############################################################################
'############################################################################

Dim DB As Database
Dim RstProjCode, rstProjMuni, rstRefCode, rstBisRow, rstOCC As Recordset
Dim strProjCode, strProjMuni, strRefCode, strBisRow, strOCC As String
Dim nRefCode, nBISrow, nOCCrow As Integer    'ProjSet no.
Dim iattr_CODE, iattr_refcode, iattr_BISrow, iattr_OCC As Integer
'Dim rcArray As Variant
Dim TblPT(0 To 2) As Double
Dim tblPT2(0 To 2) As Double
'Dim tmpArrayAss(0 To 1) As Double

'Dim tblWidth As Double
Dim txtHt As Double
Dim textObj As AcadText
Dim attributeObj As AcadAttribute
'Dim height As Double
Dim mode As Long
'Dim prompt As String

Dim nCODEHeadDwg, nREFCODEDwg, nDOBHDDwg, nDOBRowDwg, nCODEBCHDDwg As Variant
Dim nJumpHead, nJumpREFCODEROW, nJumpDOBHD, nJumpBISRow As Integer
Dim blockRefObj As AcadBlockReference
Dim BlkObj As Object
Dim k, l As Integer

'frmWorkItem.ListBox1.Clear
CreateCNstyle
TblPT(0) = 0: TblPT(1) = 0: TblPT(2) = 0
tblPT2(0) = -300: tblPT2(1) = 0: tblPT2(2) = 0
txtHt = 4
txtRow = ""
mode = acAttributeModeVerify

    nCODEHeadDwg = "\\jwja-svr-10\drawfile\jvba\XCODE_HD01.dwg"
    nREFCODEDwg = "\\jwja-svr-10\drawfile\jvba\XCODE_REFCODE_ROW01.dwg"
    nDOBHDDwg = "\\jwja-svr-10\drawfile\jvba\XCODE_DOB_HD01.dwg"
    nDOBRowDwg = "\\jwja-svr-10\drawfile\jvba\XCODE_BIS_ROW01.dwg"
    nCODEBCHDDwg = "\\jwja-svr-10\drawfile\jvba\XCODE_BC_HD01.dwg"
    nOCCTYPEROWDwg = "\\jwja-svr-10\drawfile\jvba\XCODE_OCC_ROW01.dwg"
    nCONTYPEHDDwg = "\\jwja-svr-10\drawfile\jvba\XCODE_CONTYPE_HD01.dwg"
    nCONTYPEROWDwg = "\\jwja-svr-10\drawfile\jvba\XCODE_CONTYPE_ROW01.dwg"
    nAHHDDwg = "\\jwja-svr-10\drawfile\jvba\XCODE_AH_HD01.dwg"
    nAHROWDwg = "\\jwja-svr-10\drawfile\jvba\XCODE_AH_ROW01.dwg"
    
    nJumpHead = 204 '17 X 12
    nJumpREFCODEROW = 12 '1 X 12
    nJumpDOBHD = 18
    nJumpBISRow = 24 '2 X 12
    nJumpOCCTYPEHD = 42 '2 X 12
    nJumpOCCTYPEROW = 12 '2 X 12
    nJumpCONTYPEHD = 24
    nJumpCONTYPEROW = 12
    nJumpAHHD = 36
    nJumpAHROW = 12
    
    'InsertJBlock "H:\drawfile\jvba\XCODE_HD01.dwg", tblPT, "Model"

'tblPT(1) = tblPT(1) - nJumpHead

Set DB = OpenDatabase("\\jwja-svr-10\jdb\db_misc\cl_org_outspec_02.mdb")
xProj_no = frmCode.seleproj
Debug.Print xAssID
strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, Project.TYPE, " _
& "Project.STATUS, Project.CID, PROJCODE.BLOCK, PROJCODE.LOT, PROJCODE.SECTION, " _
& "PROJCODE.MUNI, PROJCODE.ZONE, PROJCODE.LOTSIZE, PROJCODE.COVERAGE_EXISTING, " _
& "PROJCODE.COVERAGE_NEW, PROJCODE.COMMBD, PROJCODE.BIN, PROJCODE.STORY, PROJCODE.OVZONE, " _
& "PROJCODE.ZONEMAP, PROJCODE.BLDGHT_EX, PROJCODE.BLDGHT_NW, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) INNER JOIN Contact ON PROJCODE.MUNI = Contact.CID " _
& "WHERE (((PROJCODE.PROJ_NO)='" & xProj_no & "'));"

Set RstProjCode = DB.OpenRecordset(strProjCode)

RstProjCode.MoveLast
RstProjCode.MoveFirst
If RstProjCode.RecordCount = 0 Then
    GoTo Exit_writecode
End If
With RstProjCode
    
    mprojcodeID = !projcodeid
    Set blockRefObj = ThisDrawing.ModelSpace.InsertBlock _
                 (TblPT, nCODEHeadDwg, 1, 1, 1, 0) 'First dwg
    Dim varAttributes As Variant
    varAttributes = blockRefObj.GetAttributes
    For iattr_CODE = LBound(varAttributes) To UBound(varAttributes)
        Debug.Print varAttributes(iattr_CODE).TagString
'************ PROJ_NO ***************************************************************
        If varAttributes(iattr_CODE).TagString = "XPROJ_NO" Then
            If IsNull(!PROJ_NO) = True Then
                varAttributes(iattr_CODE).textString = ""
            Else
                varAttributes(iattr_CODE).textString = !PROJ_NO
                Debug.Print varAttributes(iattr_CODE).textString
            End If
        End If
'************ DATE ***************************************************************
        If varAttributes(iattr_CODE).TagString = "XDATE" Then
                varAttributes(iattr_CODE).textString = Date
        End If
'************ XPROJADDR ***************************************************************
        If varAttributes(iattr_CODE).TagString = "XPROJADDR" Then
            If IsNull(!PROJ_ADDR) = True Then
                varAttributes(iattr_CODE).textString = ""
            Else
                varAttributes(iattr_CODE).textString = !PROJ_ADDR
                Debug.Print varAttributes(iattr_CODE).textString
            End If
        End If
'************ XBLOCK ***************************************************************
        If varAttributes(iattr_CODE).TagString = "XBLOCK" Then
            If IsNull(!Block) = True Then
                varAttributes(iattr_CODE).textString = ""
            Else
                varAttributes(iattr_CODE).textString = !Block
                Debug.Print varAttributes(iattr_CODE).textString
            End If
        End If
'************ XLOT ***************************************************************
        If varAttributes(iattr_CODE).TagString = "XLOT" Then
            If IsNull(!LOT) = True Then
                varAttributes(iattr_CODE).textString = ""
            Else
                varAttributes(iattr_CODE).textString = !LOT
                Debug.Print varAttributes(iattr_CODE).textString
            End If
        End If
'************ XBIN ***************************************************************
        If varAttributes(iattr_CODE).TagString = "XBIN" Then
            If IsNull(!BIN) = True Then
                varAttributes(iattr_CODE).textString = ""
            Else
                varAttributes(iattr_CODE).textString = !BIN
                Debug.Print varAttributes(iattr_CODE).textString
            End If
        End If
'************ XCB ***************************************************************
        If varAttributes(iattr_CODE).TagString = "XCB" Then
            If IsNull(!COMMBD) = True Then
                varAttributes(iattr_CODE).textString = ""
            Else
                varAttributes(iattr_CODE).textString = !COMMBD
                Debug.Print varAttributes(iattr_CODE).textString
            End If
        End If
'************ XHT ***************************************************************
        If varAttributes(iattr_CODE).TagString = "XHT" Then
            If IsNull(!BLDGHT_EX) = True Then
                varAttributes(iattr_CODE).textString = ""
            Else
                varAttributes(iattr_CODE).textString = !BLDGHT_EX
                Debug.Print varAttributes(iattr_CODE).textString
            End If
        End If
'************ XSTORY ***************************************************************
        If varAttributes(iattr_CODE).TagString = "XSTORY" Then
            If IsNull(!STORY) = True Then
                varAttributes(iattr_CODE).textString = ""
            Else
                varAttributes(iattr_CODE).textString = !STORY
                Debug.Print varAttributes(iattr_CODE).textString
            End If
        End If
'************ XZONE ***************************************************************
        If varAttributes(iattr_CODE).TagString = "XZONE" Then
            If IsNull(!ZONE) = True Then
                varAttributes(iattr_CODE).textString = ""
            Else
                varAttributes(iattr_CODE).textString = !ZONE
                Debug.Print varAttributes(iattr_CODE).textString
            End If
        End If
'************ XLOTSIZE ***************************************************************
        If varAttributes(iattr_CODE).TagString = "XLOTSIZE" Then
            If IsNull(!LOTSIZE) = True Then
                varAttributes(iattr_CODE).textString = ""
            Else
                varAttributes(iattr_CODE).textString = Format(!LOTSIZE, "0,0") & " S.F. APPROX."
                Debug.Print varAttributes(iattr_CODE).textString
            End If
        End If
'************ XCOVERAGE_EX ***************************************************************
        If varAttributes(iattr_CODE).TagString = "XCOVERAGE_EX" Then
            If IsNull(!COVERAGE_EXISTING) = True Then
                varAttributes(iattr_CODE).textString = ""
            Else
                varAttributes(iattr_CODE).textString = !COVERAGE_EXISTING
                Debug.Print varAttributes(iattr_CODE).textString
            End If
        End If
'************ XCOVERAGE_NW ***************************************************************
        If varAttributes(iattr_CODE).TagString = "XCOVERAGE_NW" Then
            If IsNull(!COVERAGE_NEW) = True Then
                varAttributes(iattr_CODE).textString = ""
            Else
                varAttributes(iattr_CODE).textString = !COVERAGE_NEW
                Debug.Print varAttributes(iattr_CODE).textString
            End If
        End If
'************ XOVZONE ***************************************************************
        If varAttributes(iattr_CODE).TagString = "XOVZONE" Then
            If IsNull(!OVZONE) = True Then
                varAttributes(iattr_CODE).textString = ""
            Else
                varAttributes(iattr_CODE).textString = !OVZONE
                Debug.Print varAttributes(iattr_CODE).textString
            End If
        End If
'************ XMAP ***************************************************************
        If varAttributes(iattr_CODE).TagString = "XMAP" Then
            If IsNull(!ZONEMAP) = True Then
                varAttributes(iattr_CODE).textString = ""
            Else
                varAttributes(iattr_CODE).textString = !ZONEMAP
                Debug.Print varAttributes(iattr_CODE).textString
            End If
        End If
        
'************ XMUNI ***************************************************************
        If varAttributes(iattr_CODE).TagString = "XMUNI" Then
            If IsNull(!MUNI) = True Then
                varAttributes(iattr_CODE).textString = ""
            Else
                varAttributes(iattr_CODE).textString = !COMPANY
                Debug.Print varAttributes(iattr_CODE).textString
            End If
        End If
        If varAttributes(iattr_CODE).TagString = "XMUNISTREET" Then
            Debug.Print "+++++++++++++++++ Got XMUNIstreet ++++++" & varAttributes(iattr_MUNI).TagString
            If IsNull(!STREET) = True Then
                varAttributes(iattr_CODE).textString = ""
            Else
                varAttributes(iattr_CODE).textString = !STREET
                Debug.Print varAttributes(iattr_CODE).textString
            End If
        End If
        If varAttributes(iattr_CODE).TagString = "XMUNICSZ" Then
            If IsNull(!csz) = True Then
                varAttributes(iattr_CODE).textString = ""
            Else
                varAttributes(iattr_CODE).textString = !csz
                Debug.Print varAttributes(iattr_CODE).textString
            End If
        End If
        ''End With
    Next iattr_CODE
    TblPT(1) = TblPT(1) - nJumpHead
End With
RstProjCode.Close
'**********************************************************************************
'*    CODE routine
'**********************************************************************************
    
    strRefCode = "SELECT PROJCODE.PROJCODEID, CODE.CODENAME " _
    & "FROM CODE INNER JOIN (PROJCODE INNER JOIN CONNCODE ON " _
    & "PROJCODE.PROJCODEID = CONNCODE.PROJCODEID) ON CODE.CODEID = CONNCODE.CODEID " _
    & "WHERE (((PROJCODE.PROJCODEID)=" & mprojcodeID & "))"
     Set rstRefCode = DB.OpenRecordset(strRefCode)
     With rstRefCode
    nRefCode = rstRefCode.RecordCount
    .MoveLast
    .MoveFirst
nRefCode = rstRefCode.RecordCount
     For k = 1 To nRefCode
        Set blockRefObj = ThisDrawing.ModelSpace.InsertBlock _
                                     (TblPT, nREFCODEDwg, 1, 1, 1, 0)
        Dim varAttributes2 As Variant
        varAttributes2 = blockRefObj.GetAttributes
        For iattr_refcode = LBound(varAttributes2) To UBound(varAttributes2)
        
            If varAttributes2(iattr_refcode).TagString = "XCODENAME" Then
                If IsNull(!CODENAME) = True Then
                    varAttributes2(iattr_refcode).textString = ""
                Else
                    varAttributes2(iattr_refcode).textString = !CODENAME
                    Debug.Print varAttributes(iattr_refcode).textString
                End If
            End If
        
        Next iattr_refcode
        'rstRefCode.Close
        TblPT(1) = TblPT(1) - nJumpREFCODEROW
        Debug.Print "K:" & k
    .MoveNext
    Next k
    End With
    rstRefCode.Close
    Set blockRefObj = ThisDrawing.ModelSpace.InsertBlock _
                    (TblPT, nDOBHDDwg, 1, 1, 1, 0)
    TblPT(1) = TblPT(1) - nJumpDOBHD
'**********************************************************************************
'**********************************************************************************
'*    BIS routine
'**********************************************************************************
    
    strBisRow = "SELECT PROJCODE.PROJCODEID, proj_dob.bis, proj_dob.projbisnote, " _
    & "proj_dob.dobjobid, proj_dob.projbistype " _
    & "FROM PROJCODE INNER JOIN proj_dob ON PROJCODE.PROJCODEID = proj_dob.projcodeid " _
    & "WHERE (((PROJCODE.PROJCODEID)=" & mprojcodeID & "))"

     Set rstBisRow = DB.OpenRecordset(strBisRow)
     If rstBisRow.RecordCount = 0 Then
     GoTo SKIP_BISROUTINE
     
     End If
     
     With rstBisRow
     .MoveLast
     .MoveFirst
     nBISrow = rstBisRow.RecordCount
     For l = 0 To nBISrow - 1
        Set blockRefObj = ThisDrawing.ModelSpace.InsertBlock _
                                     (TblPT, nDOBRowDwg, 1, 1, 1, 0)
        Dim varAttributes3 As Variant
        varAttributes3 = blockRefObj.GetAttributes
        For iattr_BISrow = LBound(varAttributes3) To UBound(varAttributes3)
'************ XBO ***************************************************************
            'If varAttributes3(iattr_BISrow).TagString = "XBO" Then
                'If IsNull(!bisorder) = True Then '++++++++++++++++++++++++++++++++++++++++++
                    'varAttributes3(iattr_BISrow).TextString = ""
                'Else
                    'varAttributes3(iattr_BISrow).TextString = !bisorder
                    
                'End If
            'End If
'************ XBIS ***************************************************************
            If varAttributes3(iattr_BISrow).TagString = "XBIS" Then
                If IsNull(!bis) = True Then
                    varAttributes3(iattr_BISrow).textString = ""
                Else
                    varAttributes3(iattr_BISrow).textString = !bis
                    
                End If
            End If
'************ XBISTYPE ***************************************************************
            If varAttributes3(iattr_BISrow).TagString = "XBISTYPE" Then
                If IsNull(!projbistype) = True Then
                    varAttributes3(iattr_BISrow).textString = ""
                Else
                    varAttributes3(iattr_BISrow).textString = !projbistype
                    
                End If
            End If
'************ XBISDESC1 ***************************************************************
            If varAttributes3(iattr_BISrow).TagString = "XBISDESC1" Then
                If IsNull(!projbisnote) = True Then '++++++++++++++++++++++++++++++++++++++++++
                    varAttributes3(iattr_BISrow).textString = ""
                Else
                    varAttributes3(iattr_BISrow).textString = SEPTEXT2(!projbisnote, 1, 3, 33)
                    
                End If
            End If
'************ XBISDESC2 ***************************************************************
            If varAttributes3(iattr_BISrow).TagString = "XBISDESC2" Then
                If IsNull(!projbisnote) = True Then '++++++++++++++++++++++++++++++++++++++++++
                    varAttributes3(iattr_BISrow).textString = ""
                Else
                    varAttributes3(iattr_BISrow).textString = SEPTEXT2(!projbisnote, 2, 3, 33)
                    
                End If
            End If
'************ XBISDESC1 ***************************************************************
            If varAttributes3(iattr_BISrow).TagString = "XBISDESC2" Then
                If IsNull(!projbisnote) = True Then '++++++++++++++++++++++++++++++++++++++++++
                    varAttributes3(iattr_BISrow).textString = ""
                Else
                    varAttributes3(iattr_BISrow).textString = SEPTEXT2(!projbisnote, 3, 3, 33)
                    
                End If
            End If



'************ XBO ***************************************************************
        Next iattr_BISrow
        
        TblPT(1) = TblPT(1) - nJumpBISRow
    .MoveNext
    Next l
    rstBisRow.Close
    End With
SKIP_BISROUTINE:
'**********************************************************************************
'**********************************************************************************
'*    UG/OCC routine
'**********************************************************************************
'**********************************************************************************
    
Set blockRefObj = ThisDrawing.ModelSpace.InsertBlock _
                                     (TblPT, nCODEBCHDDwg, 1, 1, 1, 0)
   TblPT(1) = TblPT(1) - nJumpOCCTYPEHD
'**********************************************************************************
    'strOCC = "SELECT CONNUSEGP.PROJCODEID, CONNUSEGP.PROJUSEGPNOTE, USEGP.USEGP, USEGP.USEGPNAME, USEGP.USEGPDESC " _
& "FROM USEGP INNER JOIN (PROJCODE INNER JOIN CONNUSEGP ON PROJCODE.PROJCODEID = CONNUSEGP.PROJCODEID) ON USEGP.USEGPID = CONNUSEGP.USEGPID " _
& "WHERE (((CONNUSEGP.PROJCODEID)=" & MPROJCODEID & "));"
strOCC = "SELECT CONNOCCGRP.CONNOCCGRPID, CONNOCCGRP.OCCGRPID, CONNOCCGRP.PROJCODEID, " _
& "CONNOCCGRP.PROJOCCGRPNOTE, OCCGRP.OCCGRP, OCCGRP.OCCGRPNAME, CONNOCCGRP.PROJ_OCCLOADTYPE, " _
& "CONNOCCGRP.PROJ_OCCLOAD, CONNOCCGRP.PROJ_OCCLOADUNIT, CONNOCCGRP.ProjOccLoadNote " _
& "FROM OCCGRP INNER JOIN CONNOCCGRP ON OCCGRP.OCCGRPID = CONNOCCGRP.OCCGRPID " _
& "WHERE (((CONNOCCGRP.PROJCODEID)=" & mprojcodeID & "));"

     Set rstOCC = DB.OpenRecordset(strOCC)
     With rstOCC
     .MoveLast
    .MoveFirst
     Do While Not rstOCC.EOF
         nOCCrow = rstOCC.RecordCount
        .MoveLast
        .MoveFirst
        If rstOCC.RecordCount = 0 Then
            GoTo NoOCCStep
        End If
        
         For m = 1 To nOCCrow
            Set blockRefObj = ThisDrawing.ModelSpace.InsertBlock _
                                         (TblPT, nOCCTYPEROWDwg, 1, 1, 1, 0)
            Dim varAttributes4 As Variant
            varAttributes4 = blockRefObj.GetAttributes
            For iattr_OCC = LBound(varAttributes4) To UBound(varAttributes4)
    '************ XOCCTYPE ***************************************************************
                If varAttributes4(iattr_OCC).TagString = "XOCCTYPE" Then
                    If IsNull(!OCCGRP) = True Then '++++++++++++++++++++++++++++++++++++++++++
                        varAttributes4(iattr_OCC).textString = ""
                    Else
                        varAttributes4(iattr_OCC).textString = !OCCGRP
                        
                    End If
                End If
    '************ XOCCNAME ***************************************************************
                If varAttributes4(iattr_OCC).TagString = "XOCCNAME" Then
                    If IsNull(!OCCGRPNAME) = True Then
                        varAttributes4(iattr_OCC).textString = ""
                    Else
                        varAttributes4(iattr_OCC).textString = !OCCGRPNAME
                        
                    End If
                End If
    '************ XOCCRATE ***************************************************************
                If varAttributes4(iattr_OCC).TagString = "XOCCRATE" Then
                    If IsNull(!PROJ_OCCLOAD) = True Then
                        varAttributes4(iattr_OCC).textString = ""
                    Else
                        varAttributes4(iattr_OCC).textString = !PROJ_OCCLOAD
                        
                    End If
                End If
    '************ XOCCNOTE ***************************************************************
                If varAttributes4(iattr_OCC).TagString = "XOCCNOTE" Then
                    If IsNull(!PROJOCCGRPNOTE) = True Then
                        varAttributes4(iattr_OCC).textString = ""
                    Else
                        varAttributes4(iattr_OCC).textString = !PROJOCCGRPNOTE
                        
                    End If
                End If
    '************  ***************************************************************
            Next iattr_OCC
            
            TblPT(1) = TblPT(1) - nJumpOCCTYPEROW
        .MoveNext
        Next m
    Loop
    End With
'**********************************************************************************
'**********************************************************************************
'*    CONTYPE routine
'**********************************************************************************
'**********************************************************************************


strConType = "SELECT CONNCONTYPE.CONNCONTYPEID, CONNCONTYPE.CONTYPEID, " _
& "CONNCONTYPE.PROJCODEID, CONNCONTYPE.ProjCONTYPEnote, CONTYPE.CONTYPE, CONTYPE.CONTYPEDESC " _
& "FROM CONTYPE INNER JOIN CONNCONTYPE ON CONTYPE.CONTYPEID = CONNCONTYPE.CONTYPEID " _
& "WHERE (((CONNCONTYPE.PROJCODEID)=" & mprojcodeID & "));"


Set rstConType = DB.OpenRecordset(strConType)
With rstConType
    .MoveLast
    .MoveFirst
     Do While Not rstConType.EOF
        nCONTYPErow = rstConType.RecordCount
        If nCONTYPErow > 0 Then
            Set blockRefObj = ThisDrawing.ModelSpace.InsertBlock _
                                              (TblPT, nCONTYPEHDDwg, 1, 1, 1, 0)
            TblPT(1) = TblPT(1) - nJumpCONTYPEHD
         
         End If
         
        .MoveLast
        .MoveFirst
        If rstConType.RecordCount = 0 Then
            GoTo NoCONTYPEStep
        End If
        mCONNCONTYPEID = !CONNCONTYPEID
        MCONTYPEID = !CONTYPEID
        For O = 1 To nCONTYPErow
         
            Set blockRefObj = ThisDrawing.ModelSpace.InsertBlock _
                                         (TblPT, nCONTYPEROWDwg, 1, 1, 1, 0)
            Dim varAttributes5 As Variant
            varAttributes5 = blockRefObj.GetAttributes
            For iattr_ConType = LBound(varAttributes5) To UBound(varAttributes5)
                'mCONNCONTYPEID = CONNCONTYPEID
    '************ XOCCTYPE ***************************************************************
                If varAttributes5(iattr_ConType).TagString = "XCONTYPE" Then
                    If IsNull(!CONTYPE) = True Then '++++++++++++++++++++++++++++++++++++++++++
                        varAttributes5(iattr_ConType).textString = ""
                    Else
                        varAttributes5(iattr_ConType).textString = !CONTYPE
                        
                    End If
                End If
    '************ XOCCNAME ***************************************************************
                If varAttributes5(iattr_ConType).TagString = "XCONDESC" Then
                    If IsNull(!CONTYPEDESC) = True Then
                        varAttributes5(iattr_ConType).textString = ""
                    Else
                        varAttributes5(iattr_ConType).textString = !CONTYPEDESC
                        
                    End If
                End If
    '************ XOCCRATE ***************************************************************
                If varAttributes5(iattr_ConType).TagString = "XCONTYPENOTE" Then
                    If IsNull(!ProjCONTYPEnote) = True Then
                        varAttributes5(iattr_ConType).textString = ""
                    Else
                        varAttributes5(iattr_ConType).textString = !ProjCONTYPEnote
                        
                    End If
                 End If
    '+++++++++++++++++++++++++++++++++++++++++++++++++++++++++++++++++++++++++++++++++++++
    
            Next iattr_ConType
            
            TblPT(1) = TblPT(1) - nJumpOCCTYPEROW
                '###########################################################################
                '***************************************************************************
                '*   AREA/HT SUB ROUTINE
                '***************************************************************************
             If mCONNCONTYPEID <> "" Then
                'strAH = "SELECT CONNAREASTORY.CONNAREASTORYID, CONNAREASTORY.AREASTORYID, " _
                & "CONNAREASTORY.PROJCODEID, CONNAREASTORY.PROJAREASTORYNOTE, CONNAREASTORY.PROJADJAREA, " _
                & "CONNAREASTORY.PROJADJHT, AREASTORY.CONTYPE, AREASTORY.USEGPID, AREASTORY.HTFT, " _
                & "AREASTORY.STORY, AREASTORY.AREA, CONNAREASTORY.CONNCONTYPEID, USEGP.USEGP " _
                & "FROM (AREASTORY INNER JOIN CONNAREASTORY ON AREASTORY.ID = CONNAREASTORY.AREASTORYID) INNER JOIN USEGP ON AREASTORY.USEGPID = USEGP.USEGPID " _
                & "WHERE (((CONNAREASTORY.CONNCONTYPEID)=" & mCONNCONTYPEID & "));"
                
                'strAH = "SELECT CONNCONTYPE.CONNCONTYPEID,  OCCGRP.OCCGRP, CONNCONTYPE.CONTYPEID, CONNCONTYPE.PROJCODEID, CONNCONTYPE.ProjCONTYPEnote, CONNAREASTORY.PROJAREASTORYNOTE, " _
                & "CONNAREASTORY.PROJADJAREA, CONNAREASTORY.PROJADJHT, CONNAREASTORY.PROJADJSTORY, CONTYPE.CONTYPE, AREASTORY.HTFT, AREASTORY.STORY, AREASTORY.AREA " _
                & "FROM AREASTORY INNER JOIN ((CONTYPE INNER JOIN CONNCONTYPE ON CONTYPE.CONTYPEID = CONNCONTYPE.CONTYPEID) INNER JOIN CONNAREASTORY ON CONNCONTYPE.CONNCONTYPEID = CONNAREASTORY.CONNCONTYPEID) " _
                & "ON AREASTORY.ID = CONNAREASTORY.AREASTORYID " _
                & "WHERE (((CONNCONTYPE.CONNCONTYPEID)=" & mCONNCONTYPEID & "));"

                StrAH = "SELECT CONNCONTYPE.CONNCONTYPEID, OCCGRP.OCCGRP, CONNCONTYPE.CONTYPEID, CONNCONTYPE.PROJCODEID, CONNCONTYPE.ProjCONTYPEnote, CONNAREASTORY.PROJAREASTORYNOTE, " _
                & "CONNAREASTORY.PROJADJAREA, CONNAREASTORY.PROJADJHT, CONNAREASTORY.PROJADJSTORY, CONTYPE.CONTYPE, AREASTORY.HTFT, AREASTORY.STORY, AREASTORY.AREA " _
                & "FROM (CONTYPE INNER JOIN (AREASTORY INNER JOIN (CONNCONTYPE INNER JOIN CONNAREASTORY ON CONNCONTYPE.CONNCONTYPEID = CONNAREASTORY.CONNCONTYPEID) ON AREASTORY.ID = CONNAREASTORY.AREASTORYID) " _
                & "ON CONTYPE.CONTYPEID = CONNCONTYPE.CONTYPEID) INNER JOIN OCCGRP ON AREASTORY.occgrpID = OCCGRP.OCCGRPID " _
                & "WHERE (((CONNCONTYPE.CONNCONTYPEID)=" & mCONNCONTYPEID & "));"
                
                
                Set rstAH = DB.OpenRecordset(StrAH)
                With rstAH
                    .MoveLast
                    .MoveFirst
                     Do While Not rstAH.EOF
                        nAHrow = rstAH.RecordCount
                        If nAHrow > 0 Then
                            Set blockRefObj = ThisDrawing.ModelSpace.InsertBlock _
                                                              (TblPT, nAHHDDwg, 1, 1, 1, 0)
                            TblPT(1) = TblPT(1) - nJumpAHHD
                         
                         End If
                         
                        .MoveLast
                        .MoveFirst
                        If rstAH.RecordCount = 0 Then
                            GoTo NoAHStep
                        End If
                        
                         For P = 1 To nAHrow
                            Set blockRefObj = ThisDrawing.ModelSpace.InsertBlock _
                                                         (TblPT, nAHROWDwg, 1, 1, 1, 0)
                            Dim varAttributes6 As Variant
                            varAttributes6 = blockRefObj.GetAttributes
                            For iattr_AH = LBound(varAttributes6) To UBound(varAttributes6)
                    '************ XOCCTYPE ***************************************************************
                                If varAttributes6(iattr_AH).TagString = "XOCCTYPE" Then
                                    If IsNull(!OCCGRP) = True Then '++++++++++++++++++++++++++++++++++++++++++
                                        varAttributes6(iattr_AH).textString = ""
                                    Else
                                        varAttributes6(iattr_AH).textString = !OCCGRP
                                        
                                    End If
                                End If
                    '************ XAHHT ***************************************************************
                                If varAttributes6(iattr_AH).TagString = "XAHHT" Then
                                    If IsNull(!HTFT) = True Then
                                        varAttributes6(iattr_AH).textString = ""
                                    Else
                                        varAttributes6(iattr_AH).textString = !HTFT
                                        
                                    End If
                                End If
                    '************ XAHS ***************************************************************
                                If varAttributes6(iattr_AH).TagString = "XAHS" Then
                                    If IsNull(!STORY) = True Then
                                        varAttributes6(iattr_AH).textString = ""
                                    Else
                                        varAttributes6(iattr_AH).textString = !STORY
                                        
                                    End If
                                 End If
                    '************ XAHA ***************************************************************
                                If varAttributes6(iattr_AH).TagString = "XAHA" Then
                                    If IsNull(!Area) = True Then
                                        varAttributes6(iattr_AH).textString = ""
                                    Else
                                        varAttributes6(iattr_AH).textString = Format(!Area, "0,0") & " SF"
                                        
                                    End If
                                 End If
                    '************ XAHPHT ***************************************************************
                                If varAttributes6(iattr_AH).TagString = "XAHPHT" Then
                                    If IsNull(!PROJADJHT) = True Then
                                        varAttributes6(iattr_AH).textString = ""
                                    Else
                                        varAttributes6(iattr_AH).textString = !PROJADJHT
                                        
                                    End If
                                 End If
                    '************ XAHPS ***************************************************************
                                If varAttributes6(iattr_AH).TagString = "XAHPS" Then
                                    If IsNull(!PROJADJSTORY) = True Then
                                        varAttributes6(iattr_AH).textString = ""
                                    Else
                                        varAttributes6(iattr_AH).textString = !PROJADJSTORY
                                        
                                    End If
                                 End If
                    '************ XAHPA ***************************************************************
                                If varAttributes6(iattr_AH).TagString = "XAHPA" Then
                                    If IsNull(!PROJADJAREA) = True Then
                                        varAttributes6(iattr_AH).textString = ""
                                    Else
                                        varAttributes6(iattr_AH).textString = Format(!PROJADJAREA, "0,0") & " SF"
                                        
                                    End If
                                 End If
                    '************ XAHNOTE ***************************************************************
                                If varAttributes6(iattr_AH).TagString = "XAHNOTE" Then
                                    If IsNull(!PROJAREASTORYNOTE) = True Then
                                        varAttributes6(iattr_AH).textString = ""
                                    Else
                                        varAttributes6(iattr_AH).textString = !PROJAREASTORYNOTE
                                        
                                    End If
                                 End If

                    '************************************************************************************
                           Next iattr_AH
                            TblPT(1) = TblPT(1) - nJumpAHROW

                           .MoveNext
                        Next P
                    Loop
                End With
                rstAH.Close
                End If
                '###########################################################################
    
    '+++++++++++++++++++++++++++++++++++++++++++++++++++++++++++++++++++++++++++++++++++++
        .MoveNext
        Next O
    Loop
End With

'**********************************************************************************
'**********************************************************************************
'*    CONELEM routine
'**********************************************************************************
'**********************************************************************************





'**********************************************************************************
NoOCCStep:
    rstOCC.Close
'rstProjCode.Close
NoAHStep:
    'rstAH.Close
NoCONTYPEStep:
    rstConType.Close

Set DB = Nothing

Exit_writecode:
frmCode.Hide
End Sub

Attribute VB_Name = "Mod_DWG"
Public Sub FillSubmission()
Dim DB As Database
Dim RstDwg As Recordset
Dim strDwg As String
Dim myForm As Object
'DBEngine.SystemDB = "C:\Documents and Settings\Jinwoo\Application Data\Microsoft\Access\secured.mdw"

Set DB = OpenDatabase("\\jwja-svr-10\jdb\db_misc\X-dwg.mdb")
'------------------------------------------------------------------------
Set Screen.ActiveForm = myForm
myForm.listSubmission.Clear
'forms("frmSched_CSI").listSubmission.Clear
Screen.ActiveForm.[listSubmission].Clear
strSub = "SELECT SUBMISSION.SUBID, SUBMISSION.SUBDATE, SUBMISSION.SUBNO, SUBMISSION.SUBNAME, SUBMISSION.PROJ_NO " _
& "FROM SUBMISSION " _
& "WHERE (((SUBMISSION.PROJ_NO)='" & seleproj & "'))"
Set RstSub = DB.OpenRecordset(strSub)
Do Until RstSub.EOF = True
    listSubmission.AddItem RstSub!SUBID
    If IsNull(RstSub!subname) = False Then
    'RstSub.AddItem RstSub!subid
    listSubmission.List(listSubmission.ListCount - 1, 1) = RstSub!subname
    End If
    RstSub.MoveNext
Loop
RstSub.Close
Set RstSub = Nothing
'------------------------------------------------------------------------
ListBox4.Clear 'dwgitems

'========================================================================================
' Retired Qry 9/21/18
'========================================================================================
strDwg_old = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, DWGmain.[NO], DWGmain.proj_no, TRADE.TRADENAME " _
& "FROM TRADE INNER JOIN (DWGmain LEFT JOIN DWGGROUP ON DWGmain.DWGGROUP = DWGGROUP.GROUPNO) ON TRADE.TRADEKEY = DWGmain.TRADE " _
& "WHERE (((DWGmain.PROJ_NO) ='" & seleproj & "')) " _
& "ORDER BY TRADE.TRADENO, DWGmain.TRADE, DWGmain.DWGGROUP, Trim([trade] & [dwggroup] & ' ' & [dwgno]);"

'========================================================================================
' New Qry 9/21/18
'========================================================================================
strDwg = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, " _
& "DWGmain.[NO], DWGmain.proj_no, TRADE.TRADENAME, SUBMISSION.SUBID " _
& "FROM (TRADE INNER JOIN (DWGmain LEFT JOIN DWGGROUP ON DWGmain.DWGGROUP = DWGGROUP.GROUPNO) " _
& "ON TRADE.TRADEKEY = DWGmain.TRADE) INNER JOIN (SUBMISSION INNER JOIN SubItem ON SUBMISSION.SUBID = SubItem.subid) ON DWGmain.ID = SubItem.subdwg " _
& "WHERE (((SUBMISSION.SUBID) = '" & listSubmission & "')) " _
& "ORDER BY TRADE.TRADENO, DWGmain.TRADE, DWGmain.DWGGROUP, Trim([trade] & [dwggroup] & ' ' & [dwgno]);"



Set RstDwg = DB.OpenRecordset(strDwg)

Do Until RstDwg.EOF = True
    ListBox4.AddItem RstDwg!DWGNUMBER
    If IsNull(RstDwg!DWGNAME) = False Then
    ListBox4.List(ListBox4.ListCount - 1, 1) = RstDwg!DWGNAME
    End If
    RstDwg.MoveNext
Loop
RstDwg.Close
Set RstDwg = Nothing


DB.Close
Set DB = Nothing


End Sub

Attribute VB_Name = "Mod_Energy"
Public Sub writeEnergyInsp()


'############################################################################
'############################################################################
'#         01/19/17
'#
'#
'#
'#
'#
'############################################################################
'############################################################################

Dim DB As Database
Dim rstProjInsp As Recordset
Dim strProjInsp As String
Dim nInspRow As Integer    'ProjSet no.
Dim iattr_Insp As Integer
'Dim rcArray As Variant
Dim TblPT(0 To 2) As Double
Dim tblPT2(0 To 2) As Double
'Dim tmpArrayAss(0 To 1) As Double

'Dim tblWidth As Double
Dim txtHt As Double
Dim textObj As AcadText
Dim attributeObj As AcadAttribute
'Dim height As Double
'Dim mode As Long
'Dim prompt As String

Dim nInspHeadDwg, nInspRowDwg As Variant
Dim nJumpHead, nJumpRow As Integer
Dim blockRefObj As AcadBlockReference
Dim BlkObj As Object
Dim k, l As Integer


CreateCNstyle
TblPT(0) = 0: TblPT(1) = 0: TblPT(2) = 0
tblPT2(0) = -300: tblPT2(1) = 0: tblPT2(2) = 0
txtHt = 4
txtRow = ""
mode = acAttributeModeVerify

nInspHeadDwg = "\\jwja-svr-10\drawfile\jvba\X_INSP_HEAD_10.dwg"
nInspRowDwg = "\\jwja-svr-10\drawfile\jvba\X_INSP_ROW_10.dwg"
    
nJumpHead = 138 '11.5 X 12
'nJumpRow = 42 '3.5 X 12
nJumpRow = 60 '5 X 12
'InsertJBlock "H:\drawfile\jvba\X_WORKITEM_HEAD02.dwg", tblPT, "Model"
InsertJBlock "\\jwja-svr-10\drawfile\jvba\X_INSP_HEAD_10.dwg", TblPT, "Model"
TblPT(1) = TblPT(1) - nJumpHead

Set DB = OpenDatabase("\\jwja-svr-10\jdb\db_DOB_INSPECTIONS\X-dob_inspections_02.mdb")

xInspId = frmInsp.seleproj
Debug.Print xInspId
'strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, Project.TYPE, " _
& "Project.STATUS, Project.CID, PROJCODE.BLOCK, PROJCODE.LOT, PROJCODE.SECTION, " _
& "PROJCODE.MUNI, PROJCODE.ZONE, PROJCODE.LOTSIZE, PROJCODE.COVERAGE_EXISTING, " _
& "PROJCODE.COVERAGE_NEW, PROJCODE.COMMBD, PROJCODE.BIN, PROJCODE.STORY, PROJCODE.OVZONE, " _
& "PROJCODE.ZONEMAP, PROJCODE.BLDGHT_EX, PROJCODE.BLDGHT_NW, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) INNER JOIN Contact ON PROJCODE.MUNI = Contact.CID " _
& "WHERE (((PROJCODE.PROJ_NO)='" & xProj_no & "'));"

'******* ENERGY Query "ENG-QRY-10"
strProjInsp = "SELECT PROJINSPITEM.proj_no, PROJINSPITEM.projinspid, PROJINSPITEM.INPUT, PROJINSPITEM.INSPNOTE, " _
& "INSPECTION.INSPTYPE, INSPECTION.CODENO, INSPECTION.INSPNAME, INSPECTION.LEADDAYS, PROJINSPITEM.INSTRUCTION, " _
& "INSPECTION.INSPCRITERIOR, INSPECTION.INSPFREQ, INSPECTION.INSPREF, INSPECTION.INSPCITATION, INSPECTION.ITEM_INSTRUCTION " _
& "FROM INSPECTION INNER JOIN PROJINSPITEM ON INSPECTION.INSPID = PROJINSPITEM.INSPID " _
& "WHERE (((PROJINSPITEM.projinspid) = " & xInspId & ") AND ((INSPECTION.INSPTYPE)= 'ENERGY'))" _
& "ORDER BY INSPECTION.INSPTYPE, INSPECTION.CODENO, INSPECTION.INSPID;"


Set rstProjInsp = DB.OpenRecordset(strProjInsp)
rstProjInsp.MoveFirst
rstProjInsp.MoveLast
rstProjInsp.MoveFirst
If rstProjInsp.RecordCount = 0 Then
    GoTo Exit_writeENERGYINSP
End If
nInspRow = rstProjInsp.RecordCount

With rstProjInsp
    MPROJinspID = !PROJinspID
    For l = 0 To nInspRow - 1
    Set blockRefObj = ThisDrawing.ModelSpace.InsertBlock _
             (TblPT, nInspRowDwg, 1, 1, 1, 0) 'First dwg
             
    Dim varAttributes As Variant
    varAttributes = blockRefObj.GetAttributes
    
    For iattr_Insp = LBound(varAttributes) To UBound(varAttributes)

        Debug.Print varAttributes(iattr_Insp).TagString
'************ XTYPE ***************************************************************
        If varAttributes(iattr_Insp).TagString = "XTYPE" Then
            If IsNull(!INSPTYPE) = True Then
                varAttributes(iattr_Insp).textString = ""
            Else
                varAttributes(iattr_Insp).textString = !INSPTYPE
                Debug.Print varAttributes(iattr_Insp).textString
            End If
        End If
'************ XCODE1 ***************************************************************
        If varAttributes(iattr_Insp).TagString = "XCODE1" Then
            If IsNull(!Codeno) = True Then '++++++++++++++++++++++++++++++++++++++++++
                varAttributes(iattr_Insp).textString = ""
            Else
                varAttributes(iattr_Insp).textString = SEPTEXT2(!Codeno, 1, 2, 16)
                
            End If
        End If
'************ XCODE2 ***************************************************************
        If varAttributes(iattr_Insp).TagString = "XCODE2" Then
            If IsNull(!Codeno) = True Then '++++++++++++++++++++++++++++++++++++++++++
                varAttributes(iattr_Insp).textString = ""
            Else
                varAttributes(iattr_Insp).textString = SEPTEXT2(!Codeno, 2, 2, 16)
                
            End If
        End If
'************ XINSP1 ***************************************************************
        If varAttributes(iattr_Insp).TagString = "XINSP1" Then
            If IsNull(!INSPNAME) = True Then '++++++++++++++++++++++++++++++++++++++++++
                varAttributes(iattr_Insp).textString = ""
            Else
                varAttributes(iattr_Insp).textString = SEPTEXT2(!INSPNAME, 1, 4, 15)
            End If
        End If
'************ XINSP2 ***************************************************************
        If varAttributes(iattr_Insp).TagString = "XINSP2" Then
            If IsNull(!INSPNAME) = True Then '++++++++++++++++++++++++++++++++++++++++++
                varAttributes(iattr_Insp).textString = ""
            Else
                varAttributes(iattr_Insp).textString = SEPTEXT2(!INSPNAME, 2, 4, 15)
            End If
        End If
'************ XINSP3 ***************************************************************
        If varAttributes(iattr_Insp).TagString = "XINSP3" Then
            If IsNull(!INSPNAME) = True Then '++++++++++++++++++++++++++++++++++++++++++
                varAttributes(iattr_Insp).textString = ""
            Else
                varAttributes(iattr_Insp).textString = SEPTEXT2(!INSPNAME, 3, 4, 15)
            End If
        End If
'************ XINSP4 ***************************************************************
        If varAttributes(iattr_Insp).TagString = "XINSP4" Then
            If IsNull(!INSPNAME) = True Then '++++++++++++++++++++++++++++++++++++++++++
                varAttributes(iattr_Insp).textString = ""
            Else
                varAttributes(iattr_Insp).textString = SEPTEXT2(!INSPNAME, 4, 4, 15)
            End If
        End If

'************ XINST1 ***************************************************************
        If varAttributes(iattr_Insp).TagString = "XINST1" Then
            If IsNull(!INSPCRITERIOR) = True Then '++++++++++++++++++++++++++++++++++++++++++
                varAttributes(iattr_Insp).textString = ""
            Else
                varAttributes(iattr_Insp).textString = SEPTEXT2(!INSPCRITERIOR, 1, 8, 48)
            End If
        End If
'************ XINST2 ***************************************************************
        If varAttributes(iattr_Insp).TagString = "XINST2" Then
            If IsNull(!INSPCRITERIOR) = True Then '++++++++++++++++++++++++++++++++++++++++++
                varAttributes(iattr_Insp).textString = ""
            Else
                varAttributes(iattr_Insp).textString = SEPTEXT2(!INSPCRITERIOR, 2, 8, 48)
            End If
        End If
'************ XINST3 ***************************************************************
        If varAttributes(iattr_Insp).TagString = "XINST3" Then
            If IsNull(!INSPCRITERIOR) = True Then '++++++++++++++++++++++++++++++++++++++++++
                varAttributes(iattr_Insp).textString = ""
            Else
                varAttributes(iattr_Insp).textString = SEPTEXT2(!INSPCRITERIOR, 3, 8, 48)
            End If
        End If
'************ XINST4 ***************************************************************
        If varAttributes(iattr_Insp).TagString = "XINST4" Then
            If IsNull(!INSPCRITERIOR) = True Then '++++++++++++++++++++++++++++++++++++++++++
                varAttributes(iattr_Insp).textString = ""
            Else
                varAttributes(iattr_Insp).textString = SEPTEXT2(!INSPCRITERIOR, 4, 8, 48)
            End If
        End If
'************ XINST5 ***************************************************************
        If varAttributes(iattr_Insp).TagString = "XINST5" Then
            If IsNull(!INSPCRITERIOR) = True Then '++++++++++++++++++++++++++++++++++++++++++
                varAttributes(iattr_Insp).textString = ""
            Else
                varAttributes(iattr_Insp).textString = SEPTEXT2(!INSPCRITERIOR, 5, 8, 48)
            End If
        End If
'************ XINST6 ***************************************************************
        If varAttributes(iattr_Insp).TagString = "XINST6" Then
            If IsNull(!INSPCRITERIOR) = True Then '++++++++++++++++++++++++++++++++++++++++++
                varAttributes(iattr_Insp).textString = ""
            Else
                varAttributes(iattr_Insp).textString = SEPTEXT2(!INSPCRITERIOR, 6, 8, 48)
            End If
        End If
'************ XINST7 ***************************************************************
        If varAttributes(iattr_Insp).TagString = "XINST7" Then
            If IsNull(!INSPCRITERIOR) = True Then '++++++++++++++++++++++++++++++++++++++++++
                varAttributes(iattr_Insp).textString = ""
            Else
                varAttributes(iattr_Insp).textString = SEPTEXT2(!INSPCRITERIOR, 7, 8, 48)
            End If
        End If
'************ XINST8 ***************************************************************
        If varAttributes(iattr_Insp).TagString = "XINST8" Then
            If IsNull(!INSPCRITERIOR) = True Then '++++++++++++++++++++++++++++++++++++++++++
                varAttributes(iattr_Insp).textString = ""
            Else
                varAttributes(iattr_Insp).textString = SEPTEXT2(!INSPCRITERIOR, 8, 8, 48)
            End If
        End If

'************ XFREQ1 ***************************************************************
        If varAttributes(iattr_Insp).TagString = "XFREQ1" Then
            If IsNull(!INSPFREQ) = True Then '++++++++++++++++++++++++++++++++++++++++++
                varAttributes(iattr_Insp).textString = ""
            Else
                varAttributes(iattr_Insp).textString = SEPTEXT2(!INSPFREQ, 1, 6, 18)
            End If
        End If
'************ XFREQ2 ***************************************************************
        If varAttributes(iattr_Insp).TagString = "XFREQ2" Then
            If IsNull(!INSPFREQ) = True Then '++++++++++++++++++++++++++++++++++++++++++
                varAttributes(iattr_Insp).textString = ""
            Else
                varAttributes(iattr_Insp).textString = SEPTEXT2(!INSPFREQ, 2, 6, 18)
            End If
        End If
'************ XFREQ3 ***************************************************************
        If varAttributes(iattr_Insp).TagString = "XFREQ3" Then
            If IsNull(!INSPFREQ) = True Then '++++++++++++++++++++++++++++++++++++++++++
                varAttributes(iattr_Insp).textString = ""
            Else
                varAttributes(iattr_Insp).textString = SEPTEXT2(!INSPFREQ, 3, 6, 18)
            End If
        End If
'************ XFREQ4 ***************************************************************
        If varAttributes(iattr_Insp).TagString = "XFREQ4" Then
            If IsNull(!INSPFREQ) = True Then '++++++++++++++++++++++++++++++++++++++++++
                varAttributes(iattr_Insp).textString = ""
            Else
                varAttributes(iattr_Insp).textString = SEPTEXT2(!INSPFREQ, 4, 6, 18)
            End If
        End If
'************ XFREQ5 ***************************************************************
        If varAttributes(iattr_Insp).TagString = "XFREQ5" Then
            If IsNull(!INSPFREQ) = True Then '++++++++++++++++++++++++++++++++++++++++++
                varAttributes(iattr_Insp).textString = ""
            Else
                varAttributes(iattr_Insp).textString = SEPTEXT2(!INSPFREQ, 5, 6, 18)
            End If
        End If
'************ XFREQ6 ***************************************************************
        If varAttributes(iattr_Insp).TagString = "XFREQ6" Then
            If IsNull(!INSPFREQ) = True Then '++++++++++++++++++++++++++++++++++++++++++
                varAttributes(iattr_Insp).textString = ""
            Else
                varAttributes(iattr_Insp).textString = SEPTEXT2(!INSPFREQ, 6, 6, 18)
            End If
        End If


'************ XNOTE1 ***************************************************************
        If varAttributes(iattr_Insp).TagString = "XNOTE1" Then
            If IsNull(!INSPREF) = True Then '++++++++++++++++++++++++++++++++++++++++++
                varAttributes(iattr_Insp).textString = ""
            Else
                varAttributes(iattr_Insp).textString = SEPTEXT2(!INSPREF, 1, 6, 18)
            End If
        End If
'************ XNOTE2 ***************************************************************
        If varAttributes(iattr_Insp).TagString = "XNOTE2" Then
            If IsNull(!INSPREF) = True Then '++++++++++++++++++++++++++++++++++++++++++
                varAttributes(iattr_Insp).textString = ""
            Else
                varAttributes(iattr_Insp).textString = SEPTEXT2(!INSPREF, 2, 6, 18)
            End If
        End If
'************ XNOTE3 ***************************************************************
        If varAttributes(iattr_Insp).TagString = "XNOTE3" Then
            If IsNull(!INSPREF) = True Then '++++++++++++++++++++++++++++++++++++++++++
                varAttributes(iattr_Insp).textString = ""
            Else
                varAttributes(iattr_Insp).textString = SEPTEXT2(!INSPREF, 3, 6, 18)
            End If
        End If
'************ XNOTE4 ***************************************************************
        If varAttributes(iattr_Insp).TagString = "XNOTE4" Then
            If IsNull(!INSPREF) = True Then '++++++++++++++++++++++++++++++++++++++++++
                varAttributes(iattr_Insp).textString = ""
            Else
                varAttributes(iattr_Insp).textString = SEPTEXT2(!INSPREF, 4, 6, 18)
            End If
        End If
'************ XNOTE5 ***************************************************************
        If varAttributes(iattr_Insp).TagString = "XNOTE5" Then
            If IsNull(!INSPREF) = True Then '++++++++++++++++++++++++++++++++++++++++++
                varAttributes(iattr_Insp).textString = ""
            Else
                varAttributes(iattr_Insp).textString = SEPTEXT2(!INSPREF, 5, 6, 18)
            End If
        End If
'************ XNOTE6 ***************************************************************
        If varAttributes(iattr_Insp).TagString = "XNOTE6" Then
            If IsNull(!INSPREF) = True Then '++++++++++++++++++++++++++++++++++++++++++
                varAttributes(iattr_Insp).textString = ""
            Else
                varAttributes(iattr_Insp).textString = SEPTEXT2(!INSPREF, 6, 6, 18)
            End If
        End If
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++

'************ XECC1 ***************************************************************
        If varAttributes(iattr_Insp).TagString = "ECC1" Then
            If IsNull(!INSPCITATION) = True Then '++++++++++++++++++++++++++++++++++++++++++
                varAttributes(iattr_Insp).textString = ""
            Else
                varAttributes(iattr_Insp).textString = SEPTEXT2(!INSPCITATION, 1, 6, 18)
            End If
        End If
'************ XNOTE2 ***************************************************************
        If varAttributes(iattr_Insp).TagString = "ECC2" Then
            If IsNull(!INSPCITATION) = True Then '++++++++++++++++++++++++++++++++++++++++++
                varAttributes(iattr_Insp).textString = ""
            Else
                varAttributes(iattr_Insp).textString = SEPTEXT2(!INSPCITATION, 2, 6, 18)
            End If
        End If
'************ XNOTE3 ***************************************************************
        If varAttributes(iattr_Insp).TagString = "ECC3" Then
            If IsNull(!INSPCITATION) = True Then '++++++++++++++++++++++++++++++++++++++++++
                varAttributes(iattr_Insp).textString = ""
            Else
                varAttributes(iattr_Insp).textString = SEPTEXT2(!INSPCITATION, 3, 6, 18)
            End If
        End If
'************ XNOTE4 ***************************************************************
        If varAttributes(iattr_Insp).TagString = "ECC4" Then
            If IsNull(!INSPCITATION) = True Then '++++++++++++++++++++++++++++++++++++++++++
                varAttributes(iattr_Insp).textString = ""
            Else
                varAttributes(iattr_Insp).textString = SEPTEXT2(!INSPCITATION, 4, 6, 18)
            End If
        End If
'************ XNOTE5 ***************************************************************
        If varAttributes(iattr_Insp).TagString = "ECC5" Then
            If IsNull(!INSPCITATION) = True Then '++++++++++++++++++++++++++++++++++++++++++
                varAttributes(iattr_Insp).textString = ""
            Else
                varAttributes(iattr_Insp).textString = SEPTEXT2(!INSPCITATION, 5, 6, 18)
            End If
        End If
'************ XNOTE6 ***************************************************************
        If varAttributes(iattr_Insp).TagString = "ECC6" Then
            If IsNull(!INSPCITATION) = True Then '++++++++++++++++++++++++++++++++++++++++++
                varAttributes(iattr_Insp).textString = ""
            Else
                varAttributes(iattr_Insp).textString = SEPTEXT2(!INSPCITATION, 6, 6, 18)
            End If
        End If

'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++

'************ END TEXT INSERT LOOP ***************************************************************

    Next iattr_Insp
     TblPT(1) = TblPT(1) - nJumpRow
    .MoveNext
        
    Next l
   rstProjInsp.Close
End With

Set DB = Nothing

Exit_writeENERGYINSP:
frmInsp.Hide
End Sub
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++

Public Sub writeEnergyTabular()


'############################################################################
'############################################################################
'#         01/30/17
'#
'#
'#
'#
'#
'############################################################################
'############################################################################

Dim DB As Database
Dim rstProjECCItem As Recordset
Dim strProjECCItem As String
Dim nInspRow As Integer    'ProjSet no.
Dim iattr_Insp As Integer
'Dim rcArray As Variant
Dim TblPT(0 To 2) As Double
Dim tblPT2(0 To 2) As Double
'Dim tmpArrayAss(0 To 1) As Double

'Dim tblWidth As Double
Dim txtHt As Double
Dim textObj As AcadText
Dim attributeObj As AcadAttribute
'Dim height As Double
'Dim mode As Long
'Dim prompt As String

Dim nInspHeadDwg, nInspRowDwg As Variant
Dim nJumpHead, nJumpRow As Integer
Dim blockRefObj, blockRefObj1 As AcadBlockReference
Dim BlkObj As Object
Dim k, l As Integer


CreateCNstyle
TblPT(0) = 0: TblPT(1) = 0: TblPT(2) = 0
tblPT2(0) = -300: tblPT2(1) = 0: tblPT2(2) = 0
txtHt = 4
txtRow = ""
mode = acAttributeModeVerify

'nInspHeadDwg = "H:\drawfile\jvba\X_INSP_HEAD_10.dwg"
'nInspRowDwg = "H:\drawfile\jvba\X_INSP_ROW_10.dwg"
nInspHeadDwg = "\\jwja-svr-10\drawfile\jvba\XENGYHD05.dwg"
nInspRowDwg = "\\jwja-svr-10\drawfile\jvba\XENGYITEM05.dwg"
    
    
    
nJumpHead = 96 '11.5 X 12 ; 8 X 12
'nJumpRow = 42 '3.5 X 12
nJumpRow = 48 '5 X 12 ; 3 X 12 ; 4 X 12
'InsertJBlock "H:\drawfile\jvba\X_WORKITEM_HEAD02.dwg", tblPT, "Model"

Set DB = OpenDatabase("\\jwja-svr-10\jdb\db_DOB_INSPECTIONS\X-dob_inspections_02.mdb")

xProjECCId = frmInsp.seleProjECC
Debug.Print xProjECCId
'strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, Project.TYPE, " _
& "Project.STATUS, Project.CID, PROJCODE.BLOCK, PROJCODE.LOT, PROJCODE.SECTION, " _
& "PROJCODE.MUNI, PROJCODE.ZONE, PROJCODE.LOTSIZE, PROJCODE.COVERAGE_EXISTING, " _
& "PROJCODE.COVERAGE_NEW, PROJCODE.COMMBD, PROJCODE.BIN, PROJCODE.STORY, PROJCODE.OVZONE, " _
& "PROJCODE.ZONEMAP, PROJCODE.BLDGHT_EX, PROJCODE.BLDGHT_NW, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) INNER JOIN Contact ON PROJCODE.MUNI = Contact.CID " _
& "WHERE (((PROJCODE.PROJ_NO)='" & xProj_no & "'));"

'strProjInsp = "SELECT PROJINSPITEM.proj_no, PROJINSPITEM.projinspid, PROJINSPITEM.INPUT, PROJINSPITEM.INSPNOTE, " _
& "INSPECTION.INSPTYPE, INSPECTION.CODENO, INSPECTION.INSPNAME, INSPECTION.LEADDAYS, PROJINSPITEM.INSTRUCTION, " _
& "INSPECTION.INSPCRITERIOR, INSPECTION.INSPFREQ, INSPECTION.INSPREF, INSPECTION.INSPCITATION, INSPECTION.ITEM_INSTRUCTION " _
& "FROM INSPECTION INNER JOIN PROJINSPITEM ON INSPECTION.INSPID = PROJINSPITEM.INSPID " _
& "WHERE (((PROJINSPITEM.projinspid) = " & xInspId & ") AND ((INSPECTION.INSPTYPE)= 'ENERGY'))" _
& "ORDER BY INSPECTION.INSPTYPE, INSPECTION.CODENO, INSPECTION.INSPID;"

strProjECCItem = "SELECT PROJECC.CLIMATEZONE, PROJECC.CODE, PROJECC.ENERGYWORKSCOPE, PROJECC.PROJ_NO, PROJECCITEM.projeccitemid, PROJECCITEM.projeccid, " _
& "PROJECCITEM.ecctabid, PROJECCITEM.projeccdesc, PROJECCITEM.projeccpropvalue, " _
& "PROJECCITEM.projcodevalue, PROJECCITEM.projsuppdoc, PROJECCITEM.projnote, " _
& "PROJECCITEM.input, PROJECCITEM.projcodeid, PROJECCITEM.projcitation, PROJECCITEM.projprovision " _
& "FROM PROJECC INNER JOIN PROJECCitem ON PROJECC.projeccid = PROJECCITEM.projeccid  " _
& "WHERE (((PROJECCITEM.projeccid)= " & xProjECCId & ")); "

Set rstProjECCItem = DB.OpenRecordset(strProjECCItem)
rstProjECCItem.MoveFirst
rstProjECCItem.MoveLast
rstProjECCItem.MoveFirst
If rstProjECCItem.RecordCount = 0 Then
    GoTo Exit_writeENERGYTABULAR
End If
nInspRow = rstProjECCItem.RecordCount

With rstProjECCItem
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    'InsertJBlock "Z:\jvba\XENGYHD04.dwg", tblPT, "Model"
    Set blockRefObj1 = ThisDrawing.ModelSpace.InsertBlock _
                 (TblPT, nInspHeadDwg, 1, 1, 1, 0) 'First dwg
    TblPT(1) = TblPT(1) - nJumpHead
    Dim varAttributes1 As Variant
    'Dim EX As Integer
    varAttributes1 = blockRefObj1.GetAttributes
    'Debug.Print !PROJECC.CODE
    For iattr_Insp = LBound(varAttributes1) To UBound(varAttributes1)
    '************ PROJ_NO ***************************************************************
            If varAttributes1(iattr_Insp).TagString = "XPROJ_NO" Then
                If IsNull(!PROJ_NO) = True Then
                    varAttributes1(iattr_Insp).textString = ""
                Else
                    varAttributes1(iattr_Insp).textString = !PROJ_NO
                    Debug.Print varAttributes1(iattr_Insp).textString
                End If
            End If
    '************ XDATE ***************************************************************
            If varAttributes1(iattr_Insp).TagString = "XDATE" Then
                'If IsNull(!CODENO) = True Then '++++++++++++++++++++++++++++++++++++++++++
                    'varAttributes(iattr_Insp).TextString = ""
                'Else
                    varAttributes1(iattr_Insp).textString = Date
                    
                'End If
            End If
    '************ CLIMATE ZONE ***************************************************************
            If varAttributes1(iattr_Insp).TagString = "CLIMATEZONE" Then
                If IsNull(!climatezone) = True Then '++++++++++++++++++++++++++++++++++++++++++
                    varAttributes1(iattr_Insp).textString = ""
                Else
                    varAttributes1(iattr_Insp).textString = !climatezone
                    
                End If
            End If
    '************ CODE ***************************************************************
            If varAttributes1(iattr_Insp).TagString = "CODE" Then
                If IsNull(!CODE) = True Then '++++++++++++++++++++++++++++++++++++++++++
                    varAttributes1(iattr_Insp).textString = ""
                Else
                    varAttributes1(iattr_Insp).textString = !CODE
                    
                End If
            End If
    '************ SCOPE01 ***************************************************************
            If varAttributes1(iattr_Insp).TagString = "SCOPE01" Then
                If IsNull(!ENERGYWORKSCOPE) = True Then '++++++++++++++++++++++++++++++++++++++++++
                    varAttributes1(iattr_Insp).textString = ""
                Else
                    varAttributes1(iattr_Insp).textString = SEPTEXT2(!ENERGYWORKSCOPE, 1, 2, 40)
                    
                End If
            End If
    '************ SCOPE02 ***************************************************************
            If varAttributes1(iattr_Insp).TagString = "SCOPE02" Then
                If IsNull(!ENERGYWORKSCOPE) = True Then '++++++++++++++++++++++++++++++++++++++++++
                    varAttributes1(iattr_Insp).textString = ""
                Else
                    varAttributes1(iattr_Insp).textString = SEPTEXT2(!ENERGYWORKSCOPE, 2, 2, 40)
                    
                End If
            End If
    Next iattr_Insp
    
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    
    'MPROJinspID = !PROJinspID
    For l = 0 To nInspRow - 1
        Set blockRefObj = ThisDrawing.ModelSpace.InsertBlock _
                 (TblPT, nInspRowDwg, 1, 1, 1, 0) 'First dwg
                 
        Dim varAttributes As Variant
        Dim EX As Integer
        varAttributes = blockRefObj.GetAttributes
    
        For iattr_Insp = LBound(varAttributes) To UBound(varAttributes)
    
            Debug.Print varAttributes(iattr_Insp).TagString
            '++++++++++++++++++++++++++++++++++++++++++++++++++++++++++++++++++++++++++++++++++++++
            '++++++++++++++++++++++++++++++++++++++++++++++++++++++++++++++++++++++++++++++++++++++
            '++++++++++++++++++++++++++++++++++++++++++++++++++++++++++++++++++++++++++++++++++++++
            
            '************ CITATATION ***************************************************************
            For EX = 1 To 5
                Debug.Print Trim("ENGY_ITEM_CIT_0" & EX)
                If varAttributes(iattr_Insp).TagString = Trim("ENGY_ITEM_CIT_0" & EX) Then
                    If IsNull(!projcitation) = True Then '++++++++++++++++++++++++++++++++++++++++++
                        varAttributes(iattr_Insp).textString = ""
                    Else
                        varAttributes(iattr_Insp).textString = SEPTEXT2(!projcitation, EX, 5, 12)
                    End If
                End If
            Next EX
            '************ PROVISION projprovision***************************************************************
            For EX = 1 To 5
                Debug.Print Trim("ENGY_ITEM_PROV_0" & EX)
                If varAttributes(iattr_Insp).TagString = Trim("ENGY_ITEM_PROV_0" & EX) Then
                    If IsNull(!projprovision) = True Then '++++++++++++++++++++++++++++++++++++++++++
                        varAttributes(iattr_Insp).textString = ""
                    Else
                        varAttributes(iattr_Insp).textString = SEPTEXT2(!projprovision, EX, 5, 22)
                    End If
                End If
            Next EX
            
            '************ DESCRIPTION projeccdesc***************************************************************
            For EX = 1 To 5
                Debug.Print Trim("ENGY_ITEM_DESC_0" & EX)
                If varAttributes(iattr_Insp).TagString = Trim("ENGY_ITEM_DESC_0" & EX) Then
                    If IsNull(!projeccdesc) = True Then '++++++++++++++++++++++++++++++++++++++++++
                        varAttributes(iattr_Insp).textString = ""
                    Else
                        varAttributes(iattr_Insp).textString = SEPTEXT2(!projeccdesc, EX, 5, 22)
                    End If
                End If
            Next EX
            '************ PROPOSED VALUE projeccpropvalue***************************************************************
            
            For EX = 1 To 5
                Debug.Print Trim("ENGY_ITEM_PROPOSED_0" & EX)
                If varAttributes(iattr_Insp).TagString = Trim("ENGY_ITEM_PROPOSED_0" & EX) Then
                    If IsNull(!projeccpropvalue) = True Then '++++++++++++++++++++++++++++++++++++++++++
                        varAttributes(iattr_Insp).textString = ""
                    Else
                        varAttributes(iattr_Insp).textString = SEPTEXT2(!projeccpropvalue, EX, 5, 24)
                    End If
                End If
            Next EX
            '************ CODE VALUE projcodevalue***************************************************************
            For EX = 1 To 5
                Debug.Print Trim("ENGY_ITEM_REQUIRED_0" & EX)
                If varAttributes(iattr_Insp).TagString = Trim("ENGY_ITEM_REQUIRED_0" & EX) Then
                    If IsNull(!projcodevalue) = True Then '++++++++++++++++++++++++++++++++++++++++++
                        varAttributes(iattr_Insp).textString = ""
                    Else
                        varAttributes(iattr_Insp).textString = SEPTEXT2(!projcodevalue, EX, 5, 54)
                    End If
                End If
            Next EX
            '************ SUPPORTING DOCUMENT projsuppdoc***************************************************************
            For EX = 1 To 5
                Debug.Print Trim("ENGY_SUP_DOC_0" & EX)
                If varAttributes(iattr_Insp).TagString = Trim("ENGY_SUP_DOC_0" & EX) Then
                    If IsNull(!projsuppdoc) = True Then '++++++++++++++++++++++++++++++++++++++++++
                        varAttributes(iattr_Insp).textString = ""
                    Else
                        varAttributes(iattr_Insp).textString = SEPTEXT2(!projsuppdoc, EX, 5, 18)
                    End If
                End If
            Next EX
            
            '++++++++++++++++++++++++++++++++++++++++++++++++++++++++++++++++++++++++++++++++++++++
            '++++++++++++++++++++++++++++++++++++++++++++++++++++++++++++++++++++++++++++++++++++++
            '++++++++++++++++++++++++++++++++++++++++++++++++++++++++++++++++++++++++++++++++++++++
            
            '************ END TEXT INSERT LOOP ***************************************************************
    
        Next iattr_Insp
         TblPT(1) = TblPT(1) - nJumpRow
        .MoveNext
        
    Next l
    rstProjECCItem.Close
End With

Set DB = Nothing

Exit_writeENERGYTABULAR:
frmInsp.Hide
End Sub
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
Public Sub writeEnergyTabularXT()


'############################################################################
'############################################################################
'#         01/30/17
'#
'#
'#
'#
'#
'############################################################################
'############################################################################

Dim DB As Database
Dim rstProjECCItem As Recordset
Dim strProjECCItem As String
Dim nInspRow As Integer    'ProjSet no.
Dim iattr_Insp As Integer
'Dim rcArray As Variant
Dim TblPT(0 To 2) As Double
Dim tblPT2(0 To 2) As Double
'Dim tmpArrayAss(0 To 1) As Double

'Dim tblWidth As Double
Dim txtHt As Double
Dim textObj As AcadText
Dim attributeObj As AcadAttribute
'Dim height As Double
'Dim mode As Long
'Dim prompt As String

Dim nInspHeadDwg, nInspRowDwg, nInspRowDwgXT As Variant
Dim nJumpHead, nJumpRow As Integer
Dim blockRefObj, blockRefObj1 As AcadBlockReference
Dim BlkObj As Object
Dim k, l As Integer


CreateCNstyle
TblPT(0) = 0: TblPT(1) = 0: TblPT(2) = 0
tblPT2(0) = -300: tblPT2(1) = 0: tblPT2(2) = 0
txtHt = 4
txtRow = ""
mode = acAttributeModeVerify

'nInspHeadDwg = "H:\drawfile\jvba\X_INSP_HEAD_10.dwg"
'nInspRowDwg = "H:\drawfile\jvba\X_INSP_ROW_10.dwg"
nInspHeadDwg = "\\jwja-svr-10\drawfile\jvba\XENGYHD05.dwg"
nInspRowDwg = "\\jwja-svr-10\drawfile\jvba\XENGYITEM05.dwg"
nInspRowDwgXT = "\\jwja-svr-10\drawfile\jvba\XENGYITEM05XXT.dwg"
    
    
nJumpHead = 96 '11.5 X 12 ; 8 X 12
'nJumpRow = 42 '3.5 X 12
nJumpRow = 48 '5 X 12 ; 3 X 12 ; 4 X 12
'InsertJBlock "H:\drawfile\jvba\X_WORKITEM_HEAD02.dwg", tblPT, "Model"

Set DB = OpenDatabase("\\jwja-svr-10\jdb\db_DOB_INSPECTIONS\X-dob_inspections_02.mdb")

xProjECCId = frmInsp.seleProjECC
Debug.Print xProjECCId
'strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, Project.TYPE, " _
& "Project.STATUS, Project.CID, PROJCODE.BLOCK, PROJCODE.LOT, PROJCODE.SECTION, " _
& "PROJCODE.MUNI, PROJCODE.ZONE, PROJCODE.LOTSIZE, PROJCODE.COVERAGE_EXISTING, " _
& "PROJCODE.COVERAGE_NEW, PROJCODE.COMMBD, PROJCODE.BIN, PROJCODE.STORY, PROJCODE.OVZONE, " _
& "PROJCODE.ZONEMAP, PROJCODE.BLDGHT_EX, PROJCODE.BLDGHT_NW, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) INNER JOIN Contact ON PROJCODE.MUNI = Contact.CID " _
& "WHERE (((PROJCODE.PROJ_NO)='" & xProj_no & "'));"

'strProjInsp = "SELECT PROJINSPITEM.proj_no, PROJINSPITEM.projinspid, PROJINSPITEM.INPUT, PROJINSPITEM.INSPNOTE, " _
& "INSPECTION.INSPTYPE, INSPECTION.CODENO, INSPECTION.INSPNAME, INSPECTION.LEADDAYS, PROJINSPITEM.INSTRUCTION, " _
& "INSPECTION.INSPCRITERIOR, INSPECTION.INSPFREQ, INSPECTION.INSPREF, INSPECTION.INSPCITATION, INSPECTION.ITEM_INSTRUCTION " _
& "FROM INSPECTION INNER JOIN PROJINSPITEM ON INSPECTION.INSPID = PROJINSPITEM.INSPID " _
& "WHERE (((PROJINSPITEM.projinspid) = " & xInspId & ") AND ((INSPECTION.INSPTYPE)= 'ENERGY'))" _
& "ORDER BY INSPECTION.INSPTYPE, INSPECTION.CODENO, INSPECTION.INSPID;"

strProjECCItem = "SELECT PROJECC.CLIMATEZONE, PROJECC.CODE, PROJECC.ENERGYWORKSCOPE, PROJECC.PROJ_NO, PROJECCITEM.projeccitemid, PROJECCITEM.projeccid, " _
& "PROJECCITEM.ecctabid, PROJECCITEM.projeccdesc, PROJECCITEM.projeccpropvalue, " _
& "PROJECCITEM.projcodevalue, PROJECCITEM.projsuppdoc, PROJECCITEM.projnote, " _
& "PROJECCITEM.input, PROJECCITEM.projcodeid, PROJECCITEM.projcitation, PROJECCITEM.projprovision " _
& "FROM PROJECC INNER JOIN PROJECCitem ON PROJECC.projeccid = PROJECCITEM.projeccid  " _
& "WHERE (((PROJECCITEM.projeccid)= " & xProjECCId & ")) " _
& "ORDER BY PROJECCITEM.projcitation;"


Set rstProjECCItem = DB.OpenRecordset(strProjECCItem)
rstProjECCItem.MoveFirst
rstProjECCItem.MoveLast
rstProjECCItem.MoveFirst
If rstProjECCItem.RecordCount = 0 Then
    GoTo Exit_writeENERGYTABULAR
End If
nInspRow = rstProjECCItem.RecordCount

With rstProjECCItem
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    'InsertJBlock "Z:\jvba\XENGYHD04.dwg", tblPT, "Model"
    Set blockRefObj1 = ThisDrawing.ModelSpace.InsertBlock _
                 (TblPT, nInspHeadDwg, 1, 1, 1, 0) 'First dwg
    TblPT(1) = TblPT(1) - nJumpHead
    Dim varAttributes1 As Variant
    'Dim EX As Integer
    varAttributes1 = blockRefObj1.GetAttributes
    'Debug.Print !PROJECC.CODE
    For iattr_Insp = LBound(varAttributes1) To UBound(varAttributes1)
    '************ PROJ_NO ***************************************************************
            If varAttributes1(iattr_Insp).TagString = "XPROJ_NO" Then
                If IsNull(!PROJ_NO) = True Then
                    varAttributes1(iattr_Insp).textString = ""
                Else
                    varAttributes1(iattr_Insp).textString = !PROJ_NO
                    Debug.Print varAttributes1(iattr_Insp).textString
                End If
            End If
    '************ XDATE ***************************************************************
            If varAttributes1(iattr_Insp).TagString = "XDATE" Then
                'If IsNull(!CODENO) = True Then '++++++++++++++++++++++++++++++++++++++++++
                    'varAttributes(iattr_Insp).TextString = ""
                'Else
                    varAttributes1(iattr_Insp).textString = Date
                    
                'End If
            End If
    '************ CLIMATE ZONE ***************************************************************
            If varAttributes1(iattr_Insp).TagString = "CLIMATEZONE" Then
                If IsNull(!climatezone) = True Then '++++++++++++++++++++++++++++++++++++++++++
                    varAttributes1(iattr_Insp).textString = ""
                Else
                    varAttributes1(iattr_Insp).textString = !climatezone
                    
                End If
            End If
    '************ CODE ***************************************************************
            If varAttributes1(iattr_Insp).TagString = "CODE" Then
                If IsNull(!CODE) = True Then '++++++++++++++++++++++++++++++++++++++++++
                    varAttributes1(iattr_Insp).textString = ""
                Else
                    varAttributes1(iattr_Insp).textString = !CODE
                    
                End If
            End If
    '************ SCOPE01 ***************************************************************
            If varAttributes1(iattr_Insp).TagString = "SCOPE01" Then
                If IsNull(!ENERGYWORKSCOPE) = True Then '++++++++++++++++++++++++++++++++++++++++++
                    varAttributes1(iattr_Insp).textString = ""
                Else
                    varAttributes1(iattr_Insp).textString = SEPTEXT2(!ENERGYWORKSCOPE, 1, 2, 40)
                    
                End If
            End If
    '************ SCOPE02 ***************************************************************
            If varAttributes1(iattr_Insp).TagString = "SCOPE02" Then
                If IsNull(!ENERGYWORKSCOPE) = True Then '++++++++++++++++++++++++++++++++++++++++++
                    varAttributes1(iattr_Insp).textString = ""
                Else
                    varAttributes1(iattr_Insp).textString = SEPTEXT2(!ENERGYWORKSCOPE, 2, 2, 40)
                    
                End If
            End If
    Next iattr_Insp
    
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    
    'MPROJinspID = !PROJinspID
    For l = 0 To nInspRow - 1
        Dim mLineCount, mChrPerLine As Integer
        Dim mTotalLine As Integer
        mTotalLine = 5
        mChrPerLine = 30 'PROPOSED VALUE projeccpropvalue WAS 24
        tmpChrNo = Len(!projeccpropvalue)
        'projcodevalue
        tmpChrNo2 = Len(!projcodevalue)
        tmpLineCount = tmpChrNo / mChrPerLine
        tmpLineCount2 = tmpChrNo2 / 54
        If tmpLineCount - tmpLineCount2 > 0 Then 'use 1 or 2
        tmpLineCount = tmpLineCount
        Else
        tmpLineCount = tmpLineCount2
        End If
        Debug.Print tmpLineCount
        If tmpLineCount > 6 Then
        Debug.Print tmpChrNo
        End If
        tmpLineCount = Round(tmpLineCount)
        If tmpLineCount <= 5 Then
            mTotalLine = 5
            mLineCount = 5
        End If
        If tmpLineCount > 5 Then
            mTotalLine = 10
            mLineCount = 10
        End If



        If mLineCount >= 6 Then
           
            Set blockRefObj = ThisDrawing.ModelSpace.InsertBlock _
                     (TblPT, nInspRowDwgXT, 1, 1, 1, 0) 'First dwg
                     'tblPT(1) = tblPT(1) - nJumpRow
        
        Else
        Set blockRefObj = ThisDrawing.ModelSpace.InsertBlock _
                 (TblPT, nInspRowDwg, 1, 1, 1, 0) 'First dwg
                 
        End If
        Dim varAttributes As Variant
        Dim EX As Integer
        varAttributes = blockRefObj.GetAttributes
    
        For iattr_Insp = LBound(varAttributes) To UBound(varAttributes)
    
            Debug.Print varAttributes(iattr_Insp).TagString
            '++++++++++++++++++++++++++++++++++++++++++++++++++++++++++++++++++++++++++++++++++++++
            '++++++++++++++++++++++++++++++++++++++++++++++++++++++++++++++++++++++++++++++++++++++
            '++++++++++++++++++++++++++++++++++++++++++++++++++++++++++++++++++++++++++++++++++++++
            
            '************ CITATATION ***************************************************************
            For EX = 1 To mLineCount
                Debug.Print Trim("ENGY_ITEM_CIT_0" & EX)
                If varAttributes(iattr_Insp).TagString = Trim("ENGY_ITEM_CIT_0" & EX) Then
                    If IsNull(!projcitation) = True Then '++++++++++++++++++++++++++++++++++++++++++
                        varAttributes(iattr_Insp).textString = ""
                    Else
                        Debug.Print !projcitation & "*********************************" & EX
                        varAttributes(iattr_Insp).textString = SEPTEXT2(!projcitation, EX, mTotalLine, 12)
                    End If
                End If
            Next EX
            '************ PROVISION projprovision***************************************************************
            For EX = 1 To mLineCount
                Debug.Print Trim("ENGY_ITEM_PROV_0" & EX)
                If varAttributes(iattr_Insp).TagString = Trim("ENGY_ITEM_PROV_0" & EX) Then
                    If IsNull(!projprovision) = True Then '++++++++++++++++++++++++++++++++++++++++++
                        varAttributes(iattr_Insp).textString = ""
                    Else
                        Debug.Print !projprovision & "*********************************" & EX
                        varAttributes(iattr_Insp).textString = SEPTEXT2(!projprovision, EX, mTotalLine, 22)
                    End If
                End If
            Next EX
            
            '************ DESCRIPTION projeccdesc***************************************************************
            tmpChrNo = Len(!projeccdesc)
            
            For EX = 1 To 5
                Debug.Print Trim("ENGY_ITEM_DESC_0" & EX)
                If varAttributes(iattr_Insp).TagString = Trim("ENGY_ITEM_DESC_0" & EX) Then
                    If IsNull(!projeccdesc) = True Then '++++++++++++++++++++++++++++++++++++++++++
                        varAttributes(iattr_Insp).textString = ""
                    Else
                        Debug.Print !projeccdesc & "*********************************" & EX
                        varAttributes(iattr_Insp).textString = SEPTEXT2(!projeccdesc, EX, mTotalLine, 28)
                    End If
                End If
            Next EX
            '************ PROPOSED VALUE projeccpropvalue***************************************************************
            For EX = 1 To mLineCount
                Debug.Print Trim("ENGY_ITEM_PROPOSED_0" & EX)
                If varAttributes(iattr_Insp).TagString = Trim("ENGY_ITEM_PROPOSED_0" & EX) Then
                    If IsNull(!projeccpropvalue) = True Then '++++++++++++++++++++++++++++++++++++++++++
                        varAttributes(iattr_Insp).textString = ""
                    Else
                        Debug.Print !projeccpropvalue & "*********************************" & EX
                        varAttributes(iattr_Insp).textString = SEPTEXT2(!projeccpropvalue, EX, mTotalLine, mChrPerLine)
                        If EX = 6 Then
                        TblPT(1) = TblPT(1) - nJumpRow
                        End If
                    End If
                End If
            Next EX
            '************ CODE VALUE projcodevalue***************************************************************
            For EX = 1 To mLineCount
                Debug.Print Trim("ENGY_ITEM_REQUIRED_0" & EX)
                If varAttributes(iattr_Insp).TagString = Trim("ENGY_ITEM_REQUIRED_0" & EX) Then
                    If IsNull(!projcodevalue) = True Then '++++++++++++++++++++++++++++++++++++++++++
                        varAttributes(iattr_Insp).textString = ""
                    Else
                        varAttributes(iattr_Insp).textString = SEPTEXT2(!projcodevalue, EX, mTotalLine, 54)
                    End If
                End If
            Next EX
            '************ SUPPORTING DOCUMENT projsuppdoc***************************************************************
            For EX = 1 To mLineCount
                Debug.Print Trim("ENGY_SUP_DOC_0" & EX)
                If varAttributes(iattr_Insp).TagString = Trim("ENGY_SUP_DOC_0" & EX) Then
                    If IsNull(!projsuppdoc) = True Then '++++++++++++++++++++++++++++++++++++++++++
                        varAttributes(iattr_Insp).textString = ""
                    Else
                        varAttributes(iattr_Insp).textString = SEPTEXT2(!projsuppdoc, EX, mTotalLine, 18)
                    End If
                End If
            Next EX
            
            '++++++++++++++++++++++++++++++++++++++++++++++++++++++++++++++++++++++++++++++++++++++
            '++++++++++++++++++++++++++++++++++++++++++++++++++++++++++++++++++++++++++++++++++++++
            '++++++++++++++++++++++++++++++++++++++++++++++++++++++++++++++++++++++++++++++++++++++
            
            '************ END TEXT INSERT LOOP ***************************************************************
    
        Next iattr_Insp
         TblPT(1) = TblPT(1) - nJumpRow
        .MoveNext
        
    Next l
    rstProjECCItem.Close
End With

Set DB = Nothing

Exit_writeENERGYTABULAR:
frmInsp.Hide
End Sub
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
'++++++++++++++++++++++++++++++++++++++++++++++++++++++++++++++++++++++++++++++++++++++
Public Sub writeEnergyTabularNW()


'############################################################################
'############################################################################
'#         01/30/17 10/5/18
'#
'#
'#
'#
'#
'############################################################################
'############################################################################

Dim DB As Database
Dim rstProjECCItem As Recordset
Dim strProjECCItem, tabText, mStyleName As String
Dim nInspRow As Integer    'ProjSet no.
Dim iattr_Insp As Integer
Dim TblPT(0 To 2) As Double
Dim tblPT2(0 To 2) As Double
Dim hLineStart(0 To 2) As Double
Dim TextPosition(0 To 2) As Double
Dim rowHt(0 To 1) As Double
Dim vBar(6) As Double
Dim txtHt As Double
Dim textObj As AcadText
Dim attributeObj As AcadAttribute
Dim nInspHeadDwg, nInspRowDwg, nInspRowDwgXT As Variant
Dim nJumpHead, nJumpRow As Integer
Dim blockRefObj, blockRefObj1 As AcadBlockReference
Dim BlkObj As Object
Dim k, i As Integer
Dim wCitation, wProvision, wDesc, wDesignValue, wCodeValue, wSupDoc As Double

'Dim tmpArrayAss(0 To 1) As Double
'Dim rcArray As Variant
'Dim tblWidth As Double
'Dim height As Double
'Dim mode As Long
'Dim prompt As String
If frmInsp.OptionButton6.value Then
CreateCNstyle
mStyleName = "cn"
txtHt = 4
ElseIf frmInsp.OptionButton7.value Then
CreateARstyle
mStyleName = "ar"
txtHt = 6
End If
If frmInsp.OptionButton1.value Then
    mSCF = 48 'mSCF= Scale Factor
    If frmInsp.OptionButton6.value Then
     
     xScF = mSCF / 12

    ElseIf frmInsp.OptionButton7.value Then
        
        xScF = (mSCF / 12) * 1.5
    End If

    
    'width = mSCF * 8 '48 x 8 = 384
    wCitation = 49 ' 4'-1"
    wProvision = 80 '6'-8",
    wDesc = 80
    wDesignValue = 88
    wCodeValue = 144
    wSupDoc = 63
    

ElseIf frmInsp.OptionButton2.value Then
    mSCF = 96
    wCitation = 49 * 2 ' 4'-1"
    wProvision = 80 * 2 '6'-8",
    wDesc = 80 * 2
    wDesignValue = 88 * 2
    wCodeValue = 144 * 2
    wSupDoc = 63 * 2
    xScF = mSCF / 12
    xScFBig = xScF * 1.5
ElseIf frmInsp.OptionButton3.value Then
    mSCF = 64
    'width = mSCF * 7 '64 x 8 = 512
    xScF = mSCF / 12
ElseIf frmInsp.OptionButton4.value Then
    mSCF = 128
    'width = mSCF * 7 '64 x 8 = 512
    xScF = mSCF / 12
ElseIf frmInsp.OptionButton5.value Then
    mSCF = 192
    'width = mSCF * 7 '64 x 8 = 512
    xScF = mSCF / 12

End If
xScFBig = xScF * 1.5
'*********************************************************************************************
'*********************************************************************************************
'startPoint(0) = 0#: startPoint(1) = 0#: startPoint(2) = 0#
'SectionPoint(0) = 0#: SectionPoint(1) = 0#: SectionPoint(2) = 0#
'paraPoint(0) = 0#: paraPoint(1) = 0#: paraPoint(2) = 0#
TextPosition(0) = 0#: TextPosition(1) = 0#: TextPosition(2) = 0#
'width = 384 '32' X 12'

CodeText = ""
mChapterNo = 1
'**********************************************************************************************************
'**********************************************************************************************************

TblPT(0) = 0: TblPT(1) = 0: TblPT(2) = 0
tblPT2(0) = -300: tblPT2(1) = 0: tblPT2(2) = 0

txtRow = ""

mode = acAttributeModeVerify

'nInspHeadDwg = "H:\drawfile\jvba\X_INSP_HEAD_10.dwg"
'nInspRowDwg = "H:\drawfile\jvba\X_INSP_ROW_10.dwg"

nInspHeadDwg = "\\jwja-svr-10\drawfile\jvba\XENGYHD05.dwg"
nInspRowDwg = "\\jwja-svr-10\drawfile\jvba\XENGYITEM05.dwg"
nInspRowDwgXT = "\\jwja-svr-10\drawfile\jvba\XENGYITEM05XXT.dwg"
nENGYFOOTER = "\\jwja-svr-10\drawfile\jvba\XENGYFT03.dwg"
nJumpHead = 96 '11.5 X 12 ; 8 X 12
'nJumpRow = 42 '3.5 X 12
nJumpRow = 48 '5 X 12 ; 3 X 12 ; 4 X 12
'InsertJBlock "H:\drawfile\jvba\X_WORKITEM_HEAD02.dwg", tblPT, "Model"
indLeft = 6
indright = 4
Set DB = OpenDatabase("\\jwja-svr-10\jdb\db_DOB_INSPECTIONS\X-dob_inspections_02.mdb")

xProjECCId = frmInsp.seleProjECC
Debug.Print xProjECCId

'strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, Project.TYPE, " _
& "Project.STATUS, Project.CID, PROJCODE.BLOCK, PROJCODE.LOT, PROJCODE.SECTION, " _
& "PROJCODE.MUNI, PROJCODE.ZONE, PROJCODE.LOTSIZE, PROJCODE.COVERAGE_EXISTING, " _
& "PROJCODE.COVERAGE_NEW, PROJCODE.COMMBD, PROJCODE.BIN, PROJCODE.STORY, PROJCODE.OVZONE, " _
& "PROJCODE.ZONEMAP, PROJCODE.BLDGHT_EX, PROJCODE.BLDGHT_NW, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) INNER JOIN Contact ON PROJCODE.MUNI = Contact.CID " _
& "WHERE (((PROJCODE.PROJ_NO)='" & xProj_no & "'));"

'strProjInsp = "SELECT PROJINSPITEM.proj_no, PROJINSPITEM.projinspid, PROJINSPITEM.INPUT, PROJINSPITEM.INSPNOTE, " _
& "INSPECTION.INSPTYPE, INSPECTION.CODENO, INSPECTION.INSPNAME, INSPECTION.LEADDAYS, PROJINSPITEM.INSTRUCTION, " _
& "INSPECTION.INSPCRITERIOR, INSPECTION.INSPFREQ, INSPECTION.INSPREF, INSPECTION.INSPCITATION, INSPECTION.ITEM_INSTRUCTION " _
& "FROM INSPECTION INNER JOIN PROJINSPITEM ON INSPECTION.INSPID = PROJINSPITEM.INSPID " _
& "WHERE (((PROJINSPITEM.projinspid) = " & xInspId & ") AND ((INSPECTION.INSPTYPE)= 'ENERGY'))" _
& "ORDER BY INSPECTION.INSPTYPE, INSPECTION.CODENO, INSPECTION.INSPID;"

strProjECCItem = "SELECT PROJECC.CLIMATEZONE, PROJECC.CODE, PROJECC.ENERGYWORKSCOPE, PROJECC.PROJ_NO, PROJECCITEM.projeccitemid, PROJECCITEM.projeccid, " _
& "PROJECCITEM.ecctabid, PROJECCITEM.projeccdesc, PROJECCITEM.projeccpropvalue, " _
& "PROJECCITEM.projcodevalue, PROJECCITEM.projsuppdoc, PROJECCITEM.projnote, " _
& "PROJECCITEM.input, PROJECCITEM.projcodeid, PROJECCITEM.projcitation, PROJECCITEM.projprovision " _
& "FROM PROJECC INNER JOIN PROJECCitem ON PROJECC.projeccid = PROJECCITEM.projeccid  " _
& "WHERE (((PROJECCITEM.projeccid)= " & xProjECCId & ")) " _
& "ORDER BY PROJECCITEM.projcitation;"



Set rstProjECCItem = DB.OpenRecordset(strProjECCItem)
rstProjECCItem.MoveFirst
rstProjECCItem.MoveLast
rstProjECCItem.MoveFirst
If rstProjECCItem.RecordCount = 0 Then
    GoTo Exit_writeENERGYTABULAR
End If
nInspRow = rstProjECCItem.RecordCount

With rstProjECCItem
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    'InsertJBlock "Z:\jvba\XENGYHD04.dwg", tblPT, "Model"
    '*******************************************************************************************************
    '**************************   Write Head Block *********************************************************
    '*******************************************************************************************************
    Set blockRefObj1 = ThisDrawing.ModelSpace.InsertBlock _
    (TblPT, nInspHeadDwg, 1, 1, 1, 0) 'First dwg
    
    Dim varAttributes1 As Variant
    'Dim EX As Integer
    varAttributes1 = blockRefObj1.GetAttributes
    'Debug.Print !PROJECC.CODE
    For iattr_Insp = LBound(varAttributes1) To UBound(varAttributes1)
    '************ PROJ_NO ***************************************************************
            If varAttributes1(iattr_Insp).TagString = "XPROJ_NO" Then
                If IsNull(!PROJ_NO) = True Then
                    varAttributes1(iattr_Insp).textString = ""
                Else
                    varAttributes1(iattr_Insp).textString = !PROJ_NO
                    Debug.Print varAttributes1(iattr_Insp).textString
                End If
            End If
    '************ XDATE ***************************************************************
            If varAttributes1(iattr_Insp).TagString = "XDATE" Then
                'If IsNull(!CODENO) = True Then '++++++++++++++++++++++++++++++++++++++++++
                    'varAttributes(iattr_Insp).TextString = ""
                'Else
                    varAttributes1(iattr_Insp).textString = Date
                    
                'End If
            End If
    '************ CLIMATE ZONE ***************************************************************
            If varAttributes1(iattr_Insp).TagString = "CLIMATEZONE" Then
                If IsNull(!climatezone) = True Then '++++++++++++++++++++++++++++++++++++++++++
                    varAttributes1(iattr_Insp).textString = ""
                Else
                    varAttributes1(iattr_Insp).textString = !climatezone
                    
                End If
            End If
    '************ CODE ***************************************************************
            If varAttributes1(iattr_Insp).TagString = "CODE" Then
                If IsNull(!CODE) = True Then '++++++++++++++++++++++++++++++++++++++++++
                    varAttributes1(iattr_Insp).textString = ""
                Else
                    varAttributes1(iattr_Insp).textString = !CODE
                    
                End If
            End If
    '************ SCOPE01 ***************************************************************
            If varAttributes1(iattr_Insp).TagString = "SCOPE01" Then
                If IsNull(!ENERGYWORKSCOPE) = True Then '++++++++++++++++++++++++++++++++++++++++++
                    varAttributes1(iattr_Insp).textString = ""
                Else
                    varAttributes1(iattr_Insp).textString = SEPTEXT2(!ENERGYWORKSCOPE, 1, 2, 12)
                    
                End If
            End If
    '************ SCOPE02 ***************************************************************
            If varAttributes1(iattr_Insp).TagString = "SCOPE02" Then
                If IsNull(!ENERGYWORKSCOPE) = True Then '++++++++++++++++++++++++++++++++++++++++++
                    varAttributes1(iattr_Insp).textString = ""
                Else
                    varAttributes1(iattr_Insp).textString = SEPTEXT2(!ENERGYWORKSCOPE, 2, 2, 12)
                    
                End If
            End If
    '************ SCOPE02 ***************************************************************
    Next iattr_Insp
    
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    '++++++++++++++++++++++++++++++++++++++++++++++++++++++++++++++++++++++++++++++++++
    TblPT(1) = TblPT(1) - nJumpHead 'TblPT(1)=0
    mTab = 12
    TextPosition(0) = TblPT(0)
    TextPosition(1) = TblPT(1)
    oldrowht = TblPT(1)
    For i = 0 To nInspRow - 1 'ECC Item Count
    oldrowht = rowHt(1)
    '+++++++++++++++++++++++++++++++
    '+++++++ 1 ProjCitation+++++++++++
    '+++++++++++++++++++++++++++++++
    tabText = ""
    
    tabText = "\P" & rstProjECCItem!projcitation & "\P"
    TextPosition(0) = TextPosition(0) + indLeft
    'TextPosition(1) = TextPosition(1)
    TextPosition(1) = (Int(TextPosition(1) / 4) * 4) - 4
    vBar(0) = TextPosition(0) - indLeft
    Set mtextObj = ThisDrawing.ModelSpace.AddMText(TextPosition, wCitation - indLeft - indright, tabText)
    
    mtextObj.StyleName = mStyleName
    mtextObj.height = xScF
    
    mtextObj.Update
    mtextObj.GetBoundingBox minText, maxText
    'TextPosition(1) = minText(1)
    rowHt(0) = minText(0): rowHt(1) = minText(1) 'Set arry for minText
    Debug.Print "1) " & minText(0) & ":" & minText(1)
    'If TextPosition(1) > minText(1) Then
    rowHt(1) = minText(1)
    Debug.Print "1st. Ht.: " & rowHt(1)
    'End If

    '+++++++++++++++++++++++++++++++
    '+++++++ 2 projprovision+++++++++++
    '+++++++++++++++++++++++++++++++
    tabText = ""
    tabText = "\P" & rstProjECCItem!projprovision & "\P"
    TextPosition(0) = wCitation + indLeft
    vBar(1) = TextPosition(0) - indLeft
    'TextPosition(1) = TextPosition(1)
    'TextPosition(1) = (Int(TextPosition(1) / 4) * 4) - 4
    Set mtextObj = ThisDrawing.ModelSpace.AddMText(TextPosition, wProvision - indLeft - indright, tabText)
    mtextObj.StyleName = mStyleName
    mtextObj.height = xScF
    mtextObj.Update
    mtextObj.GetBoundingBox minText, maxText
    'TextPosition(1) = minText(1)
    'rowHt(0) = minText(0): rowHt(1) = minText(1) 'Set arry for minText
    Debug.Print "2) " & minText(0) & ":" & minText(1)
    If rowHt(1) > minText(1) Then
    Debug.Print "minText: " & minText(1)
    rowHt(1) = minText(1)
    Debug.Print "Evaled: " & rowHt(1)
    End If
    '+++++++++++++++++++++++++++++++
    '+++++++ 3 projeccdesc+++++++++++
    '+++++++++++++++++++++++++++++++
    tabText = ""
    tabText = "\P" & rstProjECCItem!projeccdesc & "\P"
    TextPosition(0) = wCitation + wProvision + indLeft
    vBar(2) = TextPosition(0) - indLeft
    'TextPosition(1) = TextPosition(1)
    'TextPosition(1) = (Int(TextPosition(1) / 4) * 4) - 4
    Set mtextObj = ThisDrawing.ModelSpace.AddMText(TextPosition, wDesc - indLeft - indright, tabText)
    mtextObj.StyleName = mStyleName
    mtextObj.height = xScF
    mtextObj.Update
    mtextObj.GetBoundingBox minText, maxText
    'TextPosition(1) = minText(1)
    'rowHt(0) = minText(0): rowHt(1) = minText(1)  'Set arry for minText
    Debug.Print "3) " & minText(0) & ":" & minText(1)
    If rowHt(1) > minText(1) Then
    Debug.Print "minText: " & minText(1)
    rowHt(1) = minText(1)
    Debug.Print "Evaled: " & rowHt(1)
    End If
    '+++++++++++++++++++++++++++++++
    '+++++++ 4 projeccpropvalue+++++++++++
    '+++++++++++++++++++++++++++++++
    tabText = ""
    tabText = "\P" & rstProjECCItem!projeccpropvalue & "\P"
    TextPosition(0) = wCitation + wProvision + wDesc + indLeft
    vBar(3) = TextPosition(0) - indLeft
    'TextPosition(1) = TextPosition(1)
    'TextPosition(1) = (Int(TextPosition(1) / 4) * 4) - 4
    Set mtextObj = ThisDrawing.ModelSpace.AddMText(TextPosition, wDesignValue - indLeft - indright, tabText)
    mtextObj.StyleName = mStyleName
    mtextObj.height = xScF
    mtextObj.Update
    mtextObj.GetBoundingBox minText, maxText
    'TextPosition(1) = minText(1)
    'rowHt(0) = minText(0): rowHt(1) = minText(1)  'Set arry for minText
    Debug.Print "4) " & minText(0) & ":" & minText(1)
    If rowHt(1) > minText(1) Then
    Debug.Print "minText: " & minText(1)
    rowHt(1) = minText(1)
    Debug.Print "Evaled: " & rowHt(1)
    End If
    '+++++++++++++++++++++++++++++++
    '+++++++ 5 projcodevalue+++++++++++
    '+++++++++++++++++++++++++++++++
    tabText = ""
    tabText = "\P" & rstProjECCItem!projcodevalue & "\P"
    TextPosition(0) = wCitation + wProvision + wDesc + wDesignValue + indLeft
    vBar(4) = TextPosition(0) - indLeft
    'TextPosition(1) = TextPosition(1)
    'TextPosition(1) = (Int(TextPosition(1) / 4) * 4) - 4
    Set mtextObj = ThisDrawing.ModelSpace.AddMText(TextPosition, wCodeValue - indLeft - indright, tabText)
    mtextObj.StyleName = mStyleName
    mtextObj.height = xScF
    mtextObj.Update
    mtextObj.GetBoundingBox minText, maxText
    'TextPosition(1) = minText(1)
    'rowHt(0) = minText(0): rowHt(1) = minText(1) 'Set arry for minText
    Debug.Print "5) " & minText(0) & ":" & minText(1)
    If rowHt(1) > minText(1) Then
    Debug.Print "minText: " & minText(1)
    rowHt(1) = minText(1)
    Debug.Print "Evaled: " & rowHt(1)
    End If
    '+++++++++++++++++++++++++++++++
    '+++++++ 6 projsuppdoc+++++++++++
    '+++++++++++++++++++++++++++++++
    tabText = ""
    tabText = "\P" & rstProjECCItem!projsuppdoc & "\P"
    TextPosition(0) = wCitation + wProvision + wDesc + wDesignValue + wCodeValue + indLeft
    vBar(5) = TextPosition(0) - indLeft
    vBar(6) = TextPosition(0) + wSupDoc - indLeft
    'TextPosition(1) = TextPosition(1)
    'TextPosition(1) = (Int(TextPosition(1) / 4) * 4) - 4
    Set mtextObj = ThisDrawing.ModelSpace.AddMText(TextPosition, wSupDoc - indLeft - indright, tabText)
    mtextObj.StyleName = mStyleName
    mtextObj.height = xScF
    mtextObj.Update
    mtextObj.GetBoundingBox minText, maxText
    'TextPosition(1) = minText(1)
    'rowHt(0) = minText(0): rowHt(1) = minText(1) 'Set arry for minText
    Debug.Print "6) " & minText(0) & ":" & minText(1)
    If rowHt(1) > minText(1) Then
    Debug.Print "minText: " & minText(1)
    rowHt(1) = minText(1)
    Debug.Print "Evaled: " & rowHt(1)
    End If
    '+++++++++++++++++++++++++++++++
    '+++++++++++++++++++++++++++++++
    '+++++++++++++++++++++++++++++++
    
    TextPosition(0) = 0#: TextPosition(1) = rowHt(1)
    Debug.Print "TextPosition(1) AFter loop: " & TextPosition(1)
    '+++++++++++++++++++++++++++++++++++++++
    '+++++++++++++++++++++++++++++++++++++++
    '+++++++++++++++++++++++++++++++++++++++
    TblPT(0) = TblPT(0)
    If i = 0 Then
        TblPT(1) = -nJumpHead
    Else
        'TblPT(1) = oldrowht
        TblPT(1) = (Int(oldrowht / 4) * 4) - 4
    End If
    tblPT2(1) = rowHt(1)
    '_________________________
    tmpY = Int(tblPT2(1) / 4)
    tblPT2(1) = (tmpY * 4) - 4
     '_________________________
    
    'TblPT(1) = rowHt(1) + oldrowht
    'oldrowht = TextPosition(1)
        For k = LBound(vBar) To UBound(vBar)
        
         
         'TblPT(0) = vBar(k): TblPT(1) = rowHt(1) + oldrowht
         TblPT(0) = vBar(k)
         tblPT2(0) = vBar(k)
         
         ThisDrawing.ModelSpace.AddLine TblPT, tblPT2
         
        
    
        Next k
    '+++++++++++++++++++++++++++++++++++++++
    '+++++++++++++++++++++++++++++++++++++++
    '+++++++++++++++++++++++++++++++++++++++
    'TextPosition(0) = 0#: TextPosition(1) = 0#: TextPosition(2) = 0#
    hLineStart(0) = 0#: hLineStart(1) = tblPT2(1): hLineStart(2) = 0#
    ThisDrawing.ModelSpace.AddLine hLineStart, tblPT2
    
    .MoveNext
    
        
    Next i
'===============================================================================
' FOOTER ENERGY
'===============================================================================

     Set blockRefObj1 = ThisDrawing.ModelSpace.InsertBlock _
    (hLineStart, nENGYFOOTER, 1, 1, 1, 0) 'First dwg
'===============================================================================

End With
Exit_writeENERGYTABULAR:
rstProjECCItem.Close
Set DB = Nothing

Exit_writeEnergyTabularNW:
frmInsp.Hide
End Sub
Public Function MaxValOfIntArray(ByRef TheArray As Variant) As Double
'This function gives max value of int array without sorting an array
Dim i As Integer
Dim MaxIntegersIndex As Integer
MaxIntegersIndex = 0

For i = 1 To UBound(TheArray)
    If TheArray(i) > TheArray(MaxIntegersIndex) Then
        MaxIntegersIndex = i
    End If
Next
'index of max value is MaxValOfIntArray
MaxValOfIntArray = TheArray(MaxIntegersIndex)
End Function

'Function Lowest(ByRef TheArray As Double) As Double
        'Dim Result As Double = Double.MaxValue
        'For Each D As Double In Array
            'If D <= Result Then Result = D
        'Next
        'Return Result
    'End Function

Attribute VB_Name = "Mod_Fixture"
Public Sub FIXTURE()

'**************************************************************
'**************************************************************
'* MOD 3/7/13 FOR PRFX NOTE
'*  MOD 9/9/14 FOR BUBBLE
'*
'**************************************************************
'**************************************************************

Dim DB As Database
Dim RstFix As Recordset
Dim strFix As String
Dim rcFix, iatFix, iatType, iatUtil As Integer
Dim TblPT(0 To 2) As Double
Dim tblPT2(0 To 2) As Double
Dim tblWidth As Double
Dim txtHt As Double
Dim textObj As AcadText
Dim attributeObj As AcadAttribute
Dim height As Double
Dim mode As Long
Dim nHeadDwg, nRowDwg, nHeadUtilDwg, nRowUtilDwg As Variant
Dim nJumpHead, nJumpRow, nJumpHeadUtil, nJumpRowUtil As Integer
'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

'Dim oSset As AcadSelectionSet



'Set DB = OpenDatabase("X:\db_misc\FIXTUREXP.mdb")
Set DB = OpenDatabase("\\jwja-svr-10\jdb\db_FIX\X-FIXTURE_17_01.mdb")
If frmSched_CSI.showfood = True Then
    '******************************************************************************************************************************************************************
    '******************************************************************************************************************************************************************

   ' strFix = "SELECT FIXITEM.FXTYPE, PROFIX.PFXID, FIXITEM.FXID, PROFIX.PFXNO, PROFIX.PROJ_NO, PROFIX.PFXRM, " _
    & "PROFIX.Pfxnote, FIXITEM.FXSUPPLIER, FIXITEM.FXMODEL, FIXITEM.FXCAT, FIXITEM.FXCOLOR, FIXITEM.FXLISTPRICE, " _
    & "PROFIX.FXDISCOUNT, PROFIX.FXPRICE, PROFIX.FXTAX, FIXITEM.FXLEAD, FIXITEM.fxnote, PROFIX.FXQTY, PROFIX.FXPRNOTE, " _
    & "Contact.COMPANY, Contact_1.COMPANY, FIXITEM.FXIMGNAME, Contact.RELATION, Contact.LAST, Contact.FIRST, " _
    & "Contact.TEL_BUS, Contact.TEL_FAX, Contact.EMAIL, Contact.STREET, Contact.CITY, Contact.STATE, Contact.ZIP, " _
    & "Contact_1.RELATION, Contact_1.LAST, Contact_1.FIRST, Contact_1.TITLE, Contact_1.TEL_BUS, Contact_1.TEL_FAX, " _
    & "Contact_1.EMAIL, Contact_1.STREET, Contact_1.CITY, Contact_1.STATE, Contact_1.ZIP, PROFIX.FXEXIST, FIXITEM.FXIMGSIM, " _
    & "PROFIX.FXPRNOTE, PROFIX.COMMENT, FIXITEM.FXNAME, Trim([CONTACT].[CITY] & ', ' & [CONTACT].[STATE] & ' ' & [CONTACT].[ZIP]) AS SCSZ, " _
    & "Trim([CONTACT_1].[CITY] & ', ' & [CONTACT_1].[STATE] & ' ' & [CONTACT_1].[ZIP]) AS MCSZ FROM ((Contact RIGHT JOIN FIXITEM ON Contact.CID = FIXITEM.FXSUPPLIER) " _
    & "LEFT JOIN Contact AS Contact_1 ON FIXITEM.FXMFGR = Contact_1.CID) INNER JOIN PROFIX ON FIXITEM.FXID = PROFIX.FXID " _
    & "WHERE (((FIXITEM.FXtype) ='" & ListBox2 & "') And ((PROFIX.PROJ_NO) ='" & seleproj & "')) " _
    & "ORDER BY PROFIX.PFXNO;"
    
    '******************************************************************************************************************************************************************
    '******************************************************************************************************************************************************************
    
    '******************************************************************************************************************************************************************
    '******************************************************************************************************************************************************************
 
    'FROM (((Contact RIGHT JOIN FIXITEM ON Contact.CID = FIXITEM.FXSUPPLIER)
    'LEFT JOIN Contact AS Contact_1 ON FIXITEM.FXMFGR = Contact_1.CID)
    'LEFT JOIN UTIL ON FIXITEM.FXID = UTIL.FXID) INNER JOIN PROFIX ON
 


    'strFix = "SELECT FIXITEM.FXTYPE, PROFIX.PFXID, FIXITEM.FXID, PROFIX.PFXNO, PROFIX.PROJ_NO, PROFIX.PFXRM, PROFIX.Pfxnote, FIXITEM.FXSUPPLIER, FIXITEM.FXMODEL, FIXITEM.FXCAT, " _
     & "FIXITEM.FXCOLOR, FIXITEM.FXLISTPRICE, PROFIX.FXDISCOUNT, PROFIX.FXPRICE, PROFIX.FXTAX, FIXITEM.FXLEAD, FIXITEM.fxnote, PROFIX.FXQTY, PROFIX.FXPRNOTE, Contact.COMPANY, " _
     & "Contact_1.COMPANY, FIXITEM.FXIMGNAME, Contact.RELATION, Contact.LAST, Contact.FIRST, Contact.TEL_BUS, Contact.TEL_FAX, Contact.EMAIL, Contact.STREET, Contact.CITY, " _
     & "Contact.STATE, Contact.ZIP, Contact_1.RELATION, Contact_1.LAST, Contact_1.FIRST, Contact_1.TITLE, Contact_1.TEL_BUS, Contact_1.TEL_FAX, Contact_1.EMAIL, " _
     & "Contact_1.STREET, Contact_1.CITY, Contact_1.STATE, Contact_1.ZIP, PROFIX.FXEXIST, FIXITEM.FXIMGSIM, PROFIX.FXPRNOTE, PROFIX.COMMENT, FIXITEM.FXNAME, " _
     & "Trim([CONTACT_1].[CITY] & ', ' & [CONTACT_1].[STATE] & ' ' & [CONTACT_1].[ZIP]) AS MCSZ, Trim([CONTACT].[CITY] & ', ' & [CONTACT].[STATE] & ' ' & [CONTACT].[ZIP]) AS SCSZ, " _
     & "UTIL.BTU, UTIL.VOLT, UTIL.AMP, UTIL.WATT, UTIL.HP, UTIL.AIRTEMP, UTIL.NEMA, UTIL.LF, " _
     & "UTIL.D, UTIL.H, UTIL.NPT, UTIL.CW, UTIL.HW, UTIL.WASTE, UTIL.CONDSIZE, UTIL.PANEL , UTIL.CIRCUIT, UTIL.PH, UTIL.UTILNOTE " _
     & "FROM (((Contact RIGHT JOIN FIXITEM ON Contact.CID = FIXITEM.FXSUPPLIER) " _
     & "LEFT JOIN Contact AS Contact_1 ON FIXITEM.FXMFGR = Contact_1.CID) " _
     & "LEFT JOIN UTIL ON FIXITEM.FXID = UTIL.FXID) INNER JOIN PROFIX ON FIXITEM.FXID = PROFIX.FXID " _
     & "WHERE (((FIXITEM.FXtype) ='" & ListBox2 & "') And ((PROFIX.PROJ_NO) ='" & seleproj & "')) " _
     & "ORDER BY FIXITEM.FXTYPE, PROFIX.PFXNO;"
    '******************************************************************************************************************************************************************
    'INNER JOIN UTIL ON FIXITEM.FXID = UTIL.FXID) INNER JOIN PROFIX ON FIXITEM.FXID = PROFIX.FXID FIXITEM.FXID = PROFIX.FXID;;;;FIXITEM.FXID = PROFIX.FXID
    '******************************************************************************************************************************************************************
    '******************************************************************************************************************************************************************
     

strFix = "SELECT PROFIX.PROFIXLISTID, PROFIX.PROJ_NO, PROFIX.PFXID, PROFIX.FXID, PROFIX.PFXNO, PROFIX.PFXRM, PROFIX.FXQTY, PROFIX.FXDISCOUNT, PROFIX.FXPRICE, " _
& "PROFIX.FXTAX , PROFIX.Pfxnote, PROFIX.FXPRNOTE, FIXITEM.FXTYPE, FIXITEM.FXMODEL, FIXITEM.FXCAT, FIXITEM.FXCOLOR, FIXITEM.FXLISTPRICE, FIXITEM.FXLEAD, " _
& "FIXITEM.FXSUPPLIER, FIXITEM.FXMFGR, FIXITEM.fxnote, Project.PROJ_NAME, Contact.Relation, Contact.COMPANY, Contact.LAST, Contact.FIRST, Contact.TITLE, " _
& "Contact.TEL_BUS, Contact.TEL_FAX, Contact.EMAIL, Contact.STREET, Contact.CITY, Contact.State, Contact.ZIP, Contact.WEBADDR, FIXITEM.FXIMGNAME, " _
& "Contact_1.CID, Contact_1.Relation, Contact_1.MR, Contact_1.LAST, Contact_1.FIRST, Contact_1.COMPANY, Contact_1.TITLE, Contact_1.TEL_BUS, " _
& "Contact_1.TEL_FAX, Contact_1.EMAIL, Contact_1.STREET, Contact_1.CITY, Contact_1.State, Contact_1.ZIP, Contact_1.NOTE, Contact_1.WEBADDR, " _
& "Trim([CONTACT_1].[CITY] & ', ' & [CONTACT_1].[STATE] & ' ' & [CONTACT_1].[ZIP]) AS MCSZ, Trim([CONTACT].[CITY] & ', ' & [CONTACT].[STATE] & ' ' & [CONTACT].[ZIP]) AS SCSZ, " _
& "FIXITEM.FXNAME, PROFIX.FXEXIST, FIXITEM.FXIMGSIM, PROFIX.COMMENT, PROFIX.FXSHIPPING, PROFIX.FXUSED, FIXITEM.FXLINK, " _
& "UTIL.BTU, UTIL.VOLT, UTIL.AMP, UTIL.WATT, UTIL.HP , UTIL.AIRTEMP, UTIL.NEMA, UTIL.LF, UTIL.D, UTIL.H, UTIL.NPT, UTIL.CW, UTIL.HW, " _
& "UTIL.WASTE, UTIL.CONDSIZE, UTIL.PANEL, UTIL.CIRCUIT, UTIL.PH, UTIL.UTILNOTE, UTIL.WT " _
& "FROM (((Contact RIGHT JOIN FIXITEM ON Contact.CID = FIXITEM.FXSUPPLIER) LEFT JOIN Contact AS Contact_1 ON FIXITEM.FXMFGR = Contact_1.CID) " _
& "RIGHT JOIN (Project RIGHT JOIN PROFIX ON Project.PROJ_NO = PROFIX.PROJ_NO) ON FIXITEM.FXID = PROFIX.FXID) left JOIN UTIL ON FIXITEM.FXID = UTIL.FXID " _
& "WHERE ((FIXITEM.FXtype) = '" & frmSched_CSI.ListBox2 & "') And ((PROFIX.PROFIXLISTID) =" & frmSched_CSI.ListBox5 & ") " _
& "ORDER BY FIXITEM.FXTYPE, PROFIX.PFXNO ; "


     
    '******************************************************************************************************************************************************************
    '******************************************************************************************************************************************************************
 
    TblPT(0) = 0: TblPT(1) = 0: TblPT(2) = 0
    tblPT2(0) = -500: tblPT2(1) = 0: tblPT2(2) = 0
    txtHt = 4
    txtRow = ""
    mode = acAttributeModeVerify
    If frmSched_CSI.showfood = True Then
        nHeadDwg = "\\jwja-svr-10\drawfile\jvba\X_FOODEQ_HD_01.dwg"
        nRowDwg = "\\jwja-svr-10\drawfile\jvba\X_FOODEQ_row_01.dwg"
        nBubdwg = "\\jwja-svr-10\drawfile\jvba\XBUBEQ_03.dwg"
        nJumpHead = 60
        nJumpRow = 60
        InsertJBlock "\\jwja-svr-10\drawfile\jvba\X_FOODEQ_HD_01.dwg", tblPT2, "Model"
    Else
        nHeadDwg = "\\jwja-svr-10\drawfile\jvba\XFIXHEAD01.dwg"
        nRowDwg = "\\jwja-svr-10\drawfile\jvba\XFIXROW01.dwg"
        nBubdwg = "\\jwja-svr-10\drawfile\jvba\XBUBEQ_03.dwg"
        nJumpHead = 48
        nJumpRow = 24
        '=========================================================================================
        nHeadUtilDwg = "\\jwja-svr-10\drawfile\jvba\XFIXHEAD03UTIL.dwg"
        nRowUtilDwg = "\\jwja-svr-10\drawfile\jvba\XFIXROW03UTIL.dwg"
        nJumpHeadUtil = 36
        nJumpRowUtil = 60
        '=========================================================================================
        
        InsertJBlock "\\jwja-svr-10\drawfile\jvba\XFIXHEAD01.dwg", tblPT2, "Model"
    
    End If


Else

'==============================================================================================================================
    'Trim(CONTACT_1.CITY & ', ' & CONTACT_1.STATE & ' ' & CONTACT_1.ZIP) AS SCSZ
    'strFix = "SELECT FIXITEM.FXTYPE, PROFIX.PFXID, FIXITEM.FXID, PROFIX.PFXNO, PROFIX.PROJ_NO, PROFIX.PFXRM, " _
    & "PROFIX.Pfxnote, FIXITEM.FXSUPPLIER, FIXITEM.FXMODEL, FIXITEM.FXCAT, FIXITEM.FXCOLOR, FIXITEM.FXLISTPRICE, " _
    & "PROFIX.FXDISCOUNT, PROFIX.FXPRICE, PROFIX.FXTAX, FIXITEM.FXLEAD, FIXITEM.fxnote, PROFIX.FXQTY, PROFIX.FXPRNOTE, " _
    & "Contact.COMPANY, Contact_1.COMPANY, FIXITEM.FXIMGNAME, Contact.RELATION, Contact.LAST, Contact.FIRST, " _
    & "Contact.TEL_BUS, Contact.TEL_FAX, Contact.EMAIL, Contact.STREET, Contact.CITY, Contact.STATE, Contact.ZIP, " _
    & "Contact_1.RELATION, Contact_1.LAST, Contact_1.FIRST, Contact_1.TITLE, Contact_1.TEL_BUS, Contact_1.TEL_FAX, " _
    & "Contact_1.EMAIL, Contact_1.STREET, Contact_1.CITY, Contact_1.STATE, Contact_1.ZIP, PROFIX.FXEXIST, FIXITEM.FXIMGSIM " _
    & "FROM ((Contact RIGHT JOIN FIXITEM ON Contact.CID = FIXITEM.FXSUPPLIER) " _
    & "LEFT JOIN Contact AS Contact_1 ON FIXITEM.FXMFGR = Contact_1.CID) INNER JOIN PROFIX ON FIXITEM.FXID = PROFIX.FXID " _
    & "WHERE (((FIXITEM.FXtype) ='" & ListBox2 & "') And ((PROFIX.PROJ_NO) ='" & seleproj & "')) " _
    & "ORDER BY PROFIX.PFXID, FIXITEM.FXID, PROFIX.PFXNO;"
'==============================================================================================================================
' Retired 11/3/18
'==============================================================================================================================

    'strFix = "SELECT FIXITEM.FXTYPE, PROFIX.PFXID, FIXITEM.FXID, PROFIX.PFXNO, PROFIX.PROJ_NO, PROFIX.PFXRM, " _
    & "PROFIX.Pfxnote, FIXITEM.FXSUPPLIER, FIXITEM.FXMODEL, FIXITEM.FXCAT, FIXITEM.FXCOLOR, FIXITEM.FXLISTPRICE, " _
    & "PROFIX.FXDISCOUNT, PROFIX.FXPRICE, PROFIX.FXTAX, FIXITEM.FXLEAD, FIXITEM.fxnote, PROFIX.FXQTY, PROFIX.FXPRNOTE, " _
    & "Contact.COMPANY, Contact_1.COMPANY, FIXITEM.FXIMGNAME, Contact.RELATION, Contact.LAST, Contact.FIRST, " _
    & "Contact.TEL_BUS, Contact.TEL_FAX, Contact.EMAIL, Contact.STREET, Contact.CITY, Contact.STATE, Contact.ZIP, " _
    & "Contact_1.RELATION, Contact_1.LAST, Contact_1.FIRST, Contact_1.TITLE, Contact_1.TEL_BUS, Contact_1.TEL_FAX, " _
    & "Contact_1.EMAIL, Contact_1.STREET, Contact_1.CITY, Contact_1.STATE, Contact_1.ZIP, PROFIX.FXEXIST, FIXITEM.FXIMGSIM, " _
    & "PROFIX.FXPRNOTE, PROFIX.COMMENT, FIXITEM.FXNAME, Trim([CONTACT].[CITY] & ', ' & [CONTACT].[STATE] & ' ' & [CONTACT].[ZIP]) AS SCSZ, " _
    & "Trim([CONTACT_1].[CITY] & ', ' & [CONTACT_1].[STATE] & ' ' & [CONTACT_1].[ZIP]) AS MCSZ FROM ((Contact RIGHT JOIN FIXITEM ON Contact.CID = FIXITEM.FXSUPPLIER) " _
    & "LEFT JOIN Contact AS Contact_1 ON FIXITEM.FXMFGR = Contact_1.CID) INNER JOIN PROFIX ON FIXITEM.FXID = PROFIX.FXID " _
    & "WHERE (((FIXITEM.FXtype) ='" & ListBox5 & "') And ((PROFIX.PROJ_NO) ='" & seleproj & "')) " _
    & "ORDER BY PROFIX.PFXNO;"
'==============================================================================================================================
Debug.Print "Listbox5: " & frmSched_CSI.ListBox5
Debug.Print "Listbox5: " & frmSched_CSI.ListBox2
strFix = "SELECT PROFIX.PROFIXLISTID, PROFIX.PROJ_NO, PROFIX.PFXID, PROFIX.FXID, PROFIX.PFXNO, PROFIX.PFXRM, PROFIX.FXQTY, PROFIX.FXDISCOUNT, " _
& "PROFIX.FXPRICE, PROFIX.FXTAX, PROFIX.Pfxnote, PROFIX.FXPRNOTE, FIXITEM.FXTYPE, FIXITEM.FXMODEL, FIXITEM.FXCAT, FIXITEM.FXCOLOR, FIXITEM.FXLISTPRICE, " _
& "FIXITEM.FXLEAD, FIXITEM.FXSUPPLIER, FIXITEM.FXMFGR, FIXITEM.fxnote, Project.PROJ_NAME, Contact.RELATION, Contact.COMPANY, Contact.LAST, Contact.FIRST, " _
& "Contact.TITLE, Contact.TEL_BUS, Contact.TEL_FAX, Contact.EMAIL, Contact.STREET, Contact.CITY, Contact.STATE, Contact.ZIP, Contact.WEBADDR, " _
& "FIXITEM.FXIMGNAME, Contact_1.CID, Contact_1.RELATION, Contact_1.MR, Contact_1.LAST, Contact_1.FIRST, Contact_1.COMPANY, Contact_1.TITLE, " _
& "Contact_1.TEL_BUS, Contact_1.TEL_FAX, Contact_1.EMAIL, Contact_1.STREET, Contact_1.CITY, Contact_1.STATE, Contact_1.ZIP, Contact_1.NOTE, Contact_1.WEBADDR, " _
& "Trim([CONTACT_1].[CITY] & ', ' & [CONTACT_1].[STATE] & ' ' & [CONTACT_1].[ZIP]) AS MCSZ, Trim([CONTACT].[CITY] & ', ' & [CONTACT].[STATE] & ' ' & [CONTACT].[ZIP]) AS SCSZ, " _
& "FIXITEM.FXNAME, PROFIX.FXEXIST, FIXITEM.FXIMGSIM, PROFIX.COMMENT, PROFIX.FXSHIPPING, PROFIX.FXUSED, FIXITEM.FXLINK " _
& "FROM ((Contact RIGHT JOIN FIXITEM ON Contact.CID = FIXITEM.FXSUPPLIER) LEFT JOIN Contact AS Contact_1 ON FIXITEM.FXMFGR = Contact_1.CID) " _
& "RIGHT JOIN (Project RIGHT JOIN PROFIX ON Project.PROJ_NO = PROFIX.PROJ_NO) ON FIXITEM.FXID = PROFIX.FXID " _
& "WHERE ((PROFIX.PROFIXLISTID) =" & frmSched_CSI.ListBox5 & ")  and ((FIXITEM.FXtype) = '" & frmSched_CSI.ListBox2 & "')" _
& "ORDER BY FIXITEM.FXTYPE, PROFIX.PFXNO;"
'==============================================================================================================================
Debug.Print "Listbox5: " & frmSched_CSI.ListBox5
    TblPT(0) = 0: TblPT(1) = 0: TblPT(2) = 0
    tblPT2(0) = -500: tblPT2(1) = 0: tblPT2(2) = 0
    txtHt = 4
    txtRow = ""
    mode = acAttributeModeVerify
    If frmSched_CSI.ShowImage = True Then
        nHeadDwg = "\\jwja-svr-10\drawfile\jvba\XFIXHEAD03.dwg"    'MOD 9/9/14
        nRowDwg = "\\jwja-svr-10\drawfile\jvba\XFIXROW03.dwg"  'MOD 9/9/14
        nBubdwg = "\\jwja-svr-10\drawfile\jvba\XBUBEQ_03.dwg"  'MOD 9/9/14
        nJumpHead = 60
        nJumpRow = 60
        nHeadUtilDwg = "\\jwja-svr-10\drawfile\jvba\XFIXHEAD03UTIL.dwg"
        nRowUtilDwg = "\\jwja-svr-10\drawfile\jvba\XFIXROW03UTIL.dwg"
        nJumpHeadUtil = 36 '3x12=36
        nJumpRowUtil = 60
        InsertJBlock "\\jwja-svr-10\drawfile\jvba\XFIXHEAD03.dwg", tblPT2, "Model"
    Else
        nHeadDwg = "\\jwja-svr-10\drawfile\jvba\XFIXHEAD01.dwg"
        nRowDwg = "\\jwja-svr-10\drawfile\jvba\XFIXROW01.dwg"
        nBubdwg = "\\jwja-svr-10\drawfile\jvba\XBUBEQ_03.dwg"  'MOD 9/9/14
        nJumpHead = 48
        nJumpRow = 24
        nHeadUtilDwg = "\\jwja-svr-10\drawfile\jvba\XFIXHEAD03UTIL.dwg"
        nRowUtilDwg = "\\jwja-svr-10\drawfile\jvba\XFIXROW03UTIL.dwg"
        nJumpHeadUtil = 36
        nJumpRowUtil = 60
        InsertJBlock "\\jwja-svr-10\drawfile\jvba\XFIXHEAD01.dwg", tblPT2, "Model"
    
    End If

End If
'ThisDrawing.ModelSpace.InsertBlock tblPT, "H:\drawfile\jvba\XFIXHEAD01.dwg", 1, 1, 1, 0
'InsertJBlock "H:\drawfile\jvba\XDWGTRADE01.dwg", tblPT2, "Model"
'InsertJBlock nHeadDwg, tblPT2, "Model"
'InsertJBlock "e:\drawfile\jvba\XHDWRFOOT02.dwg", tblPT2, "Model"
'tblPT(1) = tblPT(1) - 48

Set RstFix = DB.OpenRecordset(strFix)
rcFix = RstFix.RecordCount
Debug.Print rcFix
RstFix.MoveLast
RstFix.MoveFirst
rcFix = RstFix.RecordCount
Debug.Print rcFix
With RstFix
Set blockRefObj2 = ThisDrawing.ModelSpace.InsertBlock _
                     (TblPT, nHeadDwg, 1, 1, 1, 0)
Dim varAttributes2 As Variant
varAttributes2 = blockRefObj2.GetAttributes
For iatType = LBound(varAttributes2) To UBound(varAttributes2)

Debug.Print varAttributes2(iatType).TagString
    If varAttributes2(iatType).TagString = "XTYPE" Then
        If IsNull(!FXtype) = True Then
            varAttributes2(iatType).textString = ""
        Else
            varAttributes2(iatType).textString = !FXtype & " SCHEDULE"
            Debug.Print varAttributes2(iatType).textString
        End If
    End If
    If varAttributes2(iatType).TagString = "XPROJ_NO" Then
        If IsNull(!PROJ_NO) = True Then
            varAttributes2(iatType).textString = ""
        Else
            varAttributes2(iatType).textString = !PROJ_NO
            Debug.Print varAttributes2(iatType).textString
        End If
    End If
    If varAttributes2(iatType).TagString = "XDATE" Then
        'If IsNull(!fxtype) = True Then
            'varAttributes2(iatType).TextString = ""
        'Else
            varAttributes2(iatType).textString = Date
            Debug.Print varAttributes2(iatType).textString
        'End If
    End If

Next iatType
    TblPT(1) = TblPT(1) - nJumpHead
    For i = 1 To rcFix
        ' xHDWRSETID = !HDWRSETID
        Set blockRefObj = ThisDrawing.ModelSpace.InsertBlock _
                     (TblPT, nRowDwg, 1, 1, 1, 0)
        Dim varAttributes As Variant
        varAttributes = blockRefObj.GetAttributes
    '***************************************************************
    If !FXIMGNAME <> "" Then
    If frmSched_CSI.ShowImage = True Then

    Dim imgPT(0 To 2) As Double
    Dim scalefactor As Double
    Dim rotAngleInDegree As Double, rotAngle As Double
    'Dim imageName As String
    Dim imageName As String

    Dim raster As AcadRasterImage
    Dim imgheight As Variant
    Dim imgwidth As Variant

    'imageName = "C:\AutoCAD\sample\downtown.jpg"
    imageName = !FXIMGNAME
    Debug.Print imageName
    'insertionPoint(0) = 2#: insertionPoint(1) = 2#: insertionPoint(2) = 0#
    imgPT(0) = TblPT(0) + 36: imgPT(1) = TblPT(1) - 54: imgPT(2) = TblPT(2)
    scalefactor = 48#
    'rotAngleInDegree = 0#
    'rotAngle = rotAngleInDegree * 3.141592 / 180#
    rotAngle = 0#
    
    
    
    ' Creates a raster image in model space
    'If !fximgname <> "" Then
    Set raster = ThisDrawing.ModelSpace.AddRaster(imageName, imgPT, scalefactor, rotAngle)
        With raster
        imgheight = raster.ImageHeight
        imgwidth = raster.ImageWidth
            If imgheight > 48 Then
                xSF = (48 / imgheight) * 48
                Debug.Print "xSF: " & xSF * 48
                 raster.scalefactor = xSF
            End If
        End With
    End If
    End If
    '***************************************************************
        For iatFix = LBound(varAttributes) To UBound(varAttributes)
        
        Debug.Print varAttributes(iatFix).TagString
            If varAttributes(iatFix).TagString = "XKEY" Then 'XKEY
                If IsNull(![PFXNO]) = True Then
                    varAttributes(iatFix).textString = ""
                Else
                    varAttributes(iatFix).textString = ![PFXNO]
                    Debug.Print varAttributes(iatFix).textString
    '***************************************************************
    '*      INSERT BUBBLE
    '***************************************************************
                    TblPT(0) = TblPT(0) - 48
                    Set blockRefObj = ThisDrawing.ModelSpace.InsertBlock _
                                 (TblPT, nBubdwg, 1, 1, 1, 0)
                    Dim varAttributesB As Variant
                    varAttributesB = blockRefObj.GetAttributes
                    varAttributesB(0).textString = ![PFXNO]
                    
                    TblPT(0) = TblPT(0) + 48
    
    '***************************************************************
                End If
            End If
            If varAttributes(iatFix).TagString = "XMODEL1" Then 'XMODEL1
                If IsNull(!FXMODEL) = True Then
                    varAttributes(iatFix).textString = ""
                Else
                    'varAttributes(iatFix).TextString = SEPTEXT(!FXMODEL, 1, 2, 16)
                    varAttributes(iatFix).textString = SEPTEXT2(!FXMODEL, 1, 2, 16)
                    Debug.Print varAttributes(iatFix).textString
                End If
            End If
            If varAttributes(iatFix).TagString = "XMODEL2" Then 'XMODEL2
                If IsNull(!FXMODEL) = True Then
                    varAttributes(iatFix).textString = ""
                Else
                    'varAttributes(iatFix).TextString = SEPTEXT(!FXMODEL, 2, 2, 16)
                    varAttributes(iatFix).textString = SEPTEXT2(!FXMODEL, 2, 2, 16)
                    Debug.Print varAttributes(iatFix).textString
                End If
            End If
            If varAttributes(iatFix).TagString = "XNAME" Then 'XNAME
                If IsNull(!FXNAME) = True Then
                    varAttributes(iatFix).textString = ""
                Else
                    varAttributes(iatFix).textString = !FXNAME
                    Debug.Print varAttributes(iatFix).textString
                End If
            End If
            If varAttributes(iatFix).TagString = "XCAT" Then 'XCAT
                If IsNull(!FXCAT) = True Then
                    varAttributes(iatFix).textString = ""
                Else
                    varAttributes(iatFix).textString = !FXCAT
                    Debug.Print varAttributes(iatFix).textString
                End If
            End If
            If varAttributes(iatFix).TagString = "XFIN1" Then 'XFIN1
                If IsNull(!FXCOLOR) = True Then
                    varAttributes(iatFix).textString = ""
                Else
                    'varAttributes(iatFix).TextString = SEPTEXT(!FXCOLOR, 1, 2, 7)
                    varAttributes(iatFix).textString = SEPTEXT2(!FXCOLOR, 1, 2, 7)
                    Debug.Print varAttributes(iatFix).textString
                End If
            End If
            If varAttributes(iatFix).TagString = "XFIN2" Then 'XFIN2
                If IsNull(!FXCOLOR) = True Then
                    varAttributes(iatFix).textString = ""
                Else
                    'varAttributes(iatFix).TextString = SEPTEXT(!FXCOLOR, 2, 2, 7)
                    varAttributes(iatFix).textString = SEPTEXT2(!FXCOLOR, 2, 2, 7)
                    Debug.Print varAttributes(iatFix).textString
                End If
            End If
            
            If varAttributes(iatFix).TagString = "XMCOMP" Then 'XMCOMP
                If IsNull(![CONTACT_1.COMPANY]) = True Then
                    varAttributes(iatFix).textString = ""
                Else
                    varAttributes(iatFix).textString = Mid(![CONTACT_1.COMPANY], 1, 26)
                    Debug.Print varAttributes(iatFix).textString
                End If
            End If
            If varAttributes(iatFix).TagString = "XMSTREET" Then 'XMSTREET
                If IsNull(![CONTACT_1.STREET]) = True Then
                    varAttributes(iatFix).textString = ""
                Else
                    varAttributes(iatFix).textString = ![CONTACT_1.STREET]
                    Debug.Print varAttributes(iatFix).textString
                End If
            End If
            If varAttributes(iatFix).TagString = "XMCSZ" Then 'XMCSZ
                If !MCSZ = "," Then
                    varAttributes(iatFix).textString = ""
                Else
                    varAttributes(iatFix).textString = !MCSZ
                    Debug.Print varAttributes(iatFix).textString
                End If
            End If
            If varAttributes(iatFix).TagString = "XMTEL" Then 'XMTEL
                If IsNull(![CONTACT_1.TEL_BUS]) = True Then
                    varAttributes(iatFix).textString = ""
                Else
                    varAttributes(iatFix).textString = Format(![CONTACT_1.TEL_BUS], "###-###-####")
                    Debug.Print varAttributes(iatFix).textString
                End If
            End If
            If varAttributes(iatFix).TagString = "XSCOMP" Then 'XSCOMP
                If IsNull(![CONTACT.COMPANY]) = True Then
                    varAttributes(iatFix).textString = ""
                Else
                    varAttributes(iatFix).textString = Mid(![CONTACT.COMPANY], 1, 26)
                    Debug.Print varAttributes(iatFix).textString
                End If
            End If
            If varAttributes(iatFix).TagString = "XSSTREET" Then 'XSSTREET
                If IsNull(![CONTACT.STREET]) = True Then
                    varAttributes(iatFix).textString = ""
                Else
                    varAttributes(iatFix).textString = ![CONTACT.STREET]
                    Debug.Print varAttributes(iatFix).textString
                End If
            End If
            If varAttributes(iatFix).TagString = "XSCSZ" Then 'XSCSZ
                If !SCSZ = "," Then
                    varAttributes(iatFix).textString = ""
                Else
                    varAttributes(iatFix).textString = !SCSZ
                    Debug.Print varAttributes(iatFix).textString
                End If
            End If
            If varAttributes(iatFix).TagString = "XSTEL" Then 'XSTEL
                If IsNull(![CONTACT.TEL_BUS]) = True Then
                    varAttributes(iatFix).textString = ""
                Else
                    varAttributes(iatFix).textString = Format(![CONTACT.TEL_BUS], "###-###-####")
                    Debug.Print varAttributes(iatFix).textString
                End If
            End If
            If varAttributes(iatFix).TagString = "XNOTE1" Then 'XNOTE1 FXPRNOTE
                If IsNull(!FXPRNOTE) = True Then
                    varAttributes(iatFix).textString = ""
                Else
                    'varAttributes(iatFix).TextString = SEPTEXT(!FXPRNOTE, 1, 3, 16)
                    varAttributes(iatFix).textString = SEPTEXT2(!FXPRNOTE, 1, 3, 30)
                    Debug.Print varAttributes(iatFix).textString
                End If
            End If
            If varAttributes(iatFix).TagString = "XNOTE2" Then 'XNOTE2
                If IsNull(!FXPRNOTE) = True Then
                    varAttributes(iatFix).textString = ""
                Else
                    'varAttributes(iatFix).TextString = SEPTEXT(!FXPRNOTE, 2, 3, 16)
                    varAttributes(iatFix).textString = SEPTEXT2(!FXPRNOTE, 2, 3, 30)
                    Debug.Print varAttributes(iatFix).textString
                End If
            End If
            If varAttributes(iatFix).TagString = "XNOTE3" Then 'XNOTE3
                If IsNull(!FXPRNOTE) = True Then
                    varAttributes(iatFix).textString = ""
                Else
                    'varAttributes(iatFix).TextString = SEPTEXT(!FXPRNOTE, 3, 3, 16)
                    varAttributes(iatFix).textString = SEPTEXT2(!FXPRNOTE, 3, 3, 30)
                    Debug.Print varAttributes(iatFix).textString
                End If
            End If
   '************************************************************************************************
   '************************************************************************************************
            If varAttributes(iatFix).TagString = "XFXNOTE1" Then 'XNOTE3
                If IsNull(!fxnote) = True Then
                    varAttributes(iatFix).textString = ""
                Else
                    If showfood = True Then
                    varAttributes(iatFix).textString = SEPTEXT2(!fxnote, 1, 3, 120)
                    Else
                    varAttributes(iatFix).textString = SEPTEXT2(!fxnote, 1, 3, 30)
                    End If
                    
                    Debug.Print varAttributes(iatFix).textString
                End If
            End If
            
            If varAttributes(iatFix).TagString = "XFXNOTE2" Then 'XNOTE3
                If IsNull(!fxnote) = True Then
                    varAttributes(iatFix).textString = ""
                Else
                    If showfood = True Then
                    varAttributes(iatFix).textString = SEPTEXT2(!fxnote, 2, 3, 120)
                    Else
                    varAttributes(iatFix).textString = SEPTEXT2(!fxnote, 2, 3, 30)
                    End If
                    Debug.Print varAttributes(iatFix).textString
                End If
            End If
            
            If varAttributes(iatFix).TagString = "XFXNOTE3" Then 'XNOTE3
                If IsNull(!fxnote) = True Then
                    varAttributes(iatFix).textString = ""
                Else
                    If showfood = True Then
                    varAttributes(iatFix).textString = SEPTEXT2(!fxnote, 3, 3, 120)
                    Else
                    varAttributes(iatFix).textString = SEPTEXT2(!fxnote, 3, 3, 30)
                    End If
                    Debug.Print varAttributes(iatFix).textString
                End If
            End If

Food:
   '************************************************************************************************
   '************************************************************************************************
   '************************************ food equipments *******************************************
   '************************************************************************************************
   '************************************************************************************************
        If frmSched_CSI.showfood = True Then
            If varAttributes(iatFix).TagString = "BTU" Then 'BTU
                If IsNull(!BTU) = True Then
                    varAttributes(iatFix).textString = ""
                Else
                    varAttributes(iatFix).textString = Format(!BTU, "##,#")
                    Debug.Print varAttributes(iatFix).textString
                End If
            End If
            If varAttributes(iatFix).TagString = "NPT" Then 'BTU
                If IsNull(!NPT) = True Then
                    varAttributes(iatFix).textString = ""
                Else
                    varAttributes(iatFix).textString = !NPT
                    Debug.Print varAttributes(iatFix).textString
                End If
            End If
            If varAttributes(iatFix).TagString = "CW" Then 'BTU
                If IsNull(!CW) = True Then
                    varAttributes(iatFix).textString = ""
                Else
                    varAttributes(iatFix).textString = !CW
                    Debug.Print varAttributes(iatFix).textString
                End If
            End If
            
            If varAttributes(iatFix).TagString = "HW" Then 'HW
                If IsNull(!HW) = True Then
                    varAttributes(iatFix).textString = ""
                Else
                    varAttributes(iatFix).textString = !HW
                    Debug.Print varAttributes(iatFix).textString
                End If
            End If
            If varAttributes(iatFix).TagString = "WASTE" Then 'WASTE
                If IsNull(!WASTE) = True Then
                    varAttributes(iatFix).textString = ""
                Else
                    varAttributes(iatFix).textString = !WASTE
                    Debug.Print varAttributes(iatFix).textString
                End If
            End If
            If varAttributes(iatFix).TagString = "HP" Then 'HP
                If IsNull(!HP) = True Then
                    varAttributes(iatFix).textString = ""
                Else
                    varAttributes(iatFix).textString = !HP
                    Debug.Print varAttributes(iatFix).textString
                End If
            End If
            If varAttributes(iatFix).TagString = "WATT" Then 'WATT
                If IsNull(!WATT) = True Then
                    varAttributes(iatFix).textString = ""
                Else
                    varAttributes(iatFix).textString = Format(!WATT, "##,#")
                    Debug.Print varAttributes(iatFix).textString
                End If
            End If
            If varAttributes(iatFix).TagString = "AMP" Then 'AMP
                If IsNull(!AMP) = True Then
                    varAttributes(iatFix).textString = ""
                Else
                    varAttributes(iatFix).textString = !AMP
                    Debug.Print varAttributes(iatFix).textString
                End If
            End If
            If varAttributes(iatFix).TagString = "VOLT" Then 'VOLT
                If IsNull(!VOLT) = True Then
                    varAttributes(iatFix).textString = ""
                Else
                    varAttributes(iatFix).textString = !VOLT
                    Debug.Print varAttributes(iatFix).textString
                End If
            End If
            If varAttributes(iatFix).TagString = "PH" Then 'PH
                If IsNull(!PH) = True Then
                    varAttributes(iatFix).textString = ""
                Else
                    varAttributes(iatFix).textString = !PH
                    Debug.Print varAttributes(iatFix).textString
                End If
            End If
            If varAttributes(iatFix).TagString = "NEMA" Then 'NEMA
                If IsNull(!NEMA) = True Then
                    varAttributes(iatFix).textString = ""
                Else
                    varAttributes(iatFix).textString = !NEMA
                    Debug.Print varAttributes(iatFix).textString
                End If
            End If
            If varAttributes(iatFix).TagString = "PANEL" Then 'PANEL
                If IsNull(!PANEL) = True Then
                    varAttributes(iatFix).textString = ""
                Else
                    varAttributes(iatFix).textString = !PANEL
                    Debug.Print varAttributes(iatFix).textString
                End If
            End If
            If varAttributes(iatFix).TagString = "CIRCUIT" Then 'CIRCUIT
                If IsNull(!CIRCUIT) = True Then
                    varAttributes(iatFix).textString = ""
                Else
                    varAttributes(iatFix).textString = !CIRCUIT
                    Debug.Print varAttributes(iatFix).textString
                End If
            End If
            If varAttributes(iatFix).TagString = "AIRTEMP" Then 'AIRTEMP
                If IsNull(!AIRTEMP) = True Then
                    varAttributes(iatFix).textString = ""
                Else
                    varAttributes(iatFix).textString = !AIRTEMP
                    Debug.Print varAttributes(iatFix).textString
                End If
            End If
            If varAttributes(iatFix).TagString = "LF" Then 'LF
                If IsNull(!LF) = True Then
                    varAttributes(iatFix).textString = ""
                Else
                    varAttributes(iatFix).textString = !LF
                    Debug.Print varAttributes(iatFix).textString
                End If
            End If
            If varAttributes(iatFix).TagString = "D" Then 'D
                If IsNull(!D) = True Then
                    varAttributes(iatFix).textString = ""
                Else
                    varAttributes(iatFix).textString = !D
                    Debug.Print varAttributes(iatFix).textString
                End If
            End If
            If varAttributes(iatFix).TagString = "H" Then 'H
                If IsNull(!H) = True Then
                    varAttributes(iatFix).textString = ""
                Else
                    varAttributes(iatFix).textString = !H
                    Debug.Print varAttributes(iatFix).textString
                End If
            End If
            If varAttributes(iatFix).TagString = "UTILNOTE1" Then 'UTILNOTE1
                If IsNull(!UTILNOTE) = True Then
                    varAttributes(iatFix).textString = ""
                Else
                    varAttributes(iatFix).textString = SEPTEXT2(!UTILNOTE, 1, 3, 24)
                    Debug.Print varAttributes(iatFix).textString
                End If
            End If
            If varAttributes(iatFix).TagString = "UTILNOTE2" Then 'UTILNOTE2
                If IsNull(!UTILNOTE) = True Then
                    varAttributes(iatFix).textString = ""
                Else
                    varAttributes(iatFix).textString = SEPTEXT2(!UTILNOTE, 2, 3, 24)
                    Debug.Print varAttributes(iatFix).textString
                End If
            End If
            If varAttributes(iatFix).TagString = "UTILNOTE3" Then 'UTILNOTE3
                If IsNull(!UTILNOTE) = True Then
                    varAttributes(iatFix).textString = ""
                Else
                    varAttributes(iatFix).textString = SEPTEXT2(!UTILNOTE, 3, 3, 24)
                    Debug.Print varAttributes(iatFix).textString
                End If
            End If
            
       End If ' IF SHOWFOOD = TRUE THEN
            
            
            
            
            
            
   '************************************************************************************************
   '************************************************************************************************
   '************************************END OF food equipments *************************************
   '************************************************************************************************
   '************************************************************************************************
            
            
            
            
            'Dim selectionSet1 As AcadSelectionSet
            'Set selectionSet1 = ThisDrawing.SelectionSets. _
                        Add("NewSelectionSet")

            'ssImg = ThisDrawing.SelectionSets.Item("ImgSet").Add
            'Set rasterObj.Name = ""
            'rasterObj = ThisDrawing.modelspace.ObjectName "cadimg"
            'Set rasterObj.ImageFile = !FXIMGNAME
            
        Next iatFix
        '==================================================================================================
        '       Utility
        '==================================================================================================
        'nHeadUtilDwg = "\\jwja-svr-10\drawfile\jvba\XFIXHEAD03UTIL.dwg"
        'nRowUtilDwg = "\\jwja-svr-10\drawfile\jvba\XFIXROW03UTIL.dwg"
        'nJumpHeadUtil = 36
        'nJumpRowUtil = 60

        Dim rstUtil As Recordset
        strUtil = "SELECT UTIL.UTILID, UTIL.FXID, UTIL.BTU, UTIL.VOLT, UTIL.AMP, UTIL.WATT, UTIL.HP, UTIL.AIRTEMP, UTIL.NEMA, UTIL.LF, " _
        & "UTIL.D, UTIL.H, UTIL.NPT, UTIL.CW, UTIL.HW, UTIL.WASTE, UTIL.CONDSIZE, UTIL.PANEL, UTIL.CIRCUIT, UTIL.PH, UTIL.UTILNOTE, UTIL.WT " _
        & "FROM UTIL " _
        & "WHERE (UTIL.FXID)=" & RstFix!fxid

        Set rstUtil = DB.OpenRecordset(strUtil)
        hasutil = 0
 
         With rstUtil
            If rstUtil.EOF Then
                GoTo NoUtil
                hasutil = 0
            Else
                TblPT(1) = TblPT(1) - nJumpRow
             
                ' xHDWRSETID = !HDWRSETID
                Set blockRefObj = ThisDrawing.ModelSpace.InsertBlock _
                             (TblPT, nHeadUtilDwg, 1, 1, 1, 0)
                TblPT(1) = TblPT(1) - nJumpHeadUtil
                
                Set blockRefObj = ThisDrawing.ModelSpace.InsertBlock _
                             (TblPT, nRowUtilDwg, 1, 1, 1, 0)
                Dim varAttributesUtil As Variant
                varAttributesUtil = blockRefObj.GetAttributes
                For iatUtil = LBound(varAttributesUtil) To UBound(varAttributesUtil)
                '***************************************************************************************
                    If varAttributesUtil(iatUtil).TagString = "BTU" Then 'BTU
                        If IsNull(!BTU) = True Then
                            varAttributesUtil(iatUtil).textString = ""
                        Else
                            varAttributesUtil(iatUtil).textString = Format(!BTU, "##,#")
                            Debug.Print varAttributesUtil(iatUtil).textString
                        End If
                    End If
                    If varAttributesUtil(iatUtil).TagString = "NPT" Then 'BTU
                        If IsNull(!NPT) = True Then
                            varAttributesUtil(iatUtil).textString = ""
                        Else
                            varAttributesUtil(iatUtil).textString = !NPT
                            Debug.Print varAttributesUtil(iatUtil).textString
                        End If
                    End If
                    If varAttributesUtil(iatUtil).TagString = "CW" Then 'BTU
                        If IsNull(!CW) = True Then
                            varAttributesUtil(iatUtil).textString = ""
                        Else
                            varAttributesUtil(iatUtil).textString = !CW
                            Debug.Print varAttributesUtil(iatUtil).textString
                        End If
                    End If
                    
                    If varAttributesUtil(iatUtil).TagString = "HW" Then 'HW
                        If IsNull(!HW) = True Then
                            varAttributesUtil(iatUtil).textString = ""
                        Else
                            varAttributesUtil(iatUtil).textString = !HW
                            Debug.Print varAttributesUtil(iatUtil).textString
                        End If
                    End If
                    If varAttributesUtil(iatUtil).TagString = "WASTE" Then 'WASTE
                        If IsNull(!WASTE) = True Then
                            varAttributesUtil(iatUtil).textString = ""
                        Else
                            varAttributesUtil(iatUtil).textString = !WASTE
                            Debug.Print varAttributesUtil(iatUtil).textString
                        End If
                    End If
                    If varAttributesUtil(iatUtil).TagString = "HP" Then 'HP
                        If IsNull(!HP) = True Then
                            varAttributesUtil(iatUtil).textString = ""
                        Else
                            varAttributesUtil(iatUtil).textString = !HP
                            Debug.Print varAttributesUtil(iatUtil).textString
                        End If
                    End If
                    If varAttributesUtil(iatUtil).TagString = "WATT" Then 'WATT
                        If IsNull(!WATT) = True Then
                            varAttributesUtil(iatUtil).textString = ""
                        Else
                            varAttributesUtil(iatUtil).textString = Format(!WATT, "##,#")
                            Debug.Print varAttributesUtil(iatUtil).textString
                        End If
                    End If
                    If varAttributesUtil(iatUtil).TagString = "AMP" Then 'AMP
                        If IsNull(!AMP) = True Then
                            varAttributesUtil(iatUtil).textString = ""
                        Else
                            varAttributesUtil(iatUtil).textString = !AMP
                            Debug.Print varAttributesUtil(iatUtil).textString
                        End If
                    End If
                    If varAttributesUtil(iatUtil).TagString = "VOLT" Then 'VOLT
                        If IsNull(!VOLT) = True Then
                            varAttributesUtil(iatUtil).textString = ""
                        Else
                            varAttributesUtil(iatUtil).textString = !VOLT
                            Debug.Print varAttributesUtil(iatUtil).textString
                        End If
                    End If
                    If varAttributesUtil(iatUtil).TagString = "PH" Then 'PH
                        If IsNull(!PH) = True Then
                            varAttributesUtil(iatUtil).textString = ""
                        Else
                            varAttributesUtil(iatUtil).textString = !PH
                            Debug.Print varAttributesUtil(iatUtil).textString
                        End If
                    End If
                    If varAttributesUtil(iatUtil).TagString = "NEMA" Then 'NEMA
                        If IsNull(!NEMA) = True Then
                            varAttributesUtil(iatUtil).textString = ""
                        Else
                            varAttributesUtil(iatUtil).textString = !NEMA
                            Debug.Print varAttributesUtil(iatUtil).textString
                        End If
                    End If
                    If varAttributesUtil(iatUtil).TagString = "PANEL" Then 'PANEL
                        If IsNull(!PANEL) = True Then
                            varAttributesUtil(iatUtil).textString = ""
                        Else
                            varAttributesUtil(iatUtil).textString = !PANEL
                            Debug.Print varAttributesUtil(iatUtil).textString
                        End If
                    End If
                    If varAttributesUtil(iatUtil).TagString = "CIRCUIT" Then 'CIRCUIT
                        If IsNull(!CIRCUIT) = True Then
                            varAttributesUtil(iatUtil).textString = ""
                        Else
                            varAttributesUtil(iatUtil).textString = !CIRCUIT
                            Debug.Print varAttributesUtil(iatUtil).textString
                        End If
                    End If
                    If varAttributesUtil(iatUtil).TagString = "AIRTEMP" Then 'AIRTEMP
                        If IsNull(!AIRTEMP) = True Then
                            varAttributesUtil(iatUtil).textString = ""
                        Else
                            varAttributesUtil(iatUtil).textString = !AIRTEMP
                            Debug.Print varAttributesUtil(iatUtil).textString
                        End If
                    End If
                    If varAttributesUtil(iatUtil).TagString = "LF" Then 'LF
                        If IsNull(!LF) = True Then
                            varAttributesUtil(iatUtil).textString = ""
                        Else
                            varAttributesUtil(iatUtil).textString = !LF
                            Debug.Print varAttributesUtil(iatUtil).textString
                        End If
                    End If
                    If varAttributesUtil(iatUtil).TagString = "D" Then 'D
                        If IsNull(!D) = True Then
                            varAttributesUtil(iatUtil).textString = ""
                        Else
                            varAttributesUtil(iatUtil).textString = !D
                            Debug.Print varAttributesUtil(iatUtil).textString
                        End If
                    End If
                    If varAttributesUtil(iatUtil).TagString = "H" Then 'H
                        If IsNull(!H) = True Then
                            varAttributesUtil(iatUtil).textString = ""
                        Else
                            varAttributesUtil(iatUtil).textString = !H
                            Debug.Print varAttributesUtil(iatUtil).textString
                        End If
                    End If
                    If varAttributesUtil(iatUtil).TagString = "WT" Then 'WT
                        If IsNull(!WT) = True Then
                            varAttributesUtil(iatUtil).textString = ""
                        Else
                            varAttributesUtil(iatUtil).textString = !WT
                            Debug.Print varAttributesUtil(iatUtil).textString
                        End If
                    End If
                    If varAttributesUtil(iatUtil).TagString = "UTILNOTE1" Then 'UTILNOTE1
                        If IsNull(!UTILNOTE) = True Then
                            varAttributesUtil(iatUtil).textString = ""
                        Else
                            varAttributesUtil(iatUtil).textString = SEPTEXT2(!UTILNOTE, 1, 3, 56)
                            Debug.Print varAttributesUtil(iatUtil).textString
                        End If
                    End If
                    If varAttributesUtil(iatUtil).TagString = "UTILNOTE2" Then 'UTILNOTE2
                        If IsNull(!UTILNOTE) = True Then
                            varAttributesUtil(iatUtil).textString = ""
                        Else
                            varAttributesUtil(iatUtil).textString = SEPTEXT2(!UTILNOTE, 2, 3, 56)
                            Debug.Print varAttributesUtil(iatUtil).textString
                        End If
                    End If
                    If varAttributesUtil(iatUtil).TagString = "UTILNOTE3" Then 'UTILNOTE3
                        If IsNull(!UTILNOTE) = True Then
                            varAttributesUtil(iatUtil).textString = ""
                        Else
                            varAttributesUtil(iatUtil).textString = SEPTEXT2(!UTILNOTE, 3, 3, 56)
                            Debug.Print varAttributesUtil(iatUtil).textString
                        End If
                    End If
               
                '***************************************************************************************
                Next iatUtil
            End If
        End With
        TblPT(1) = TblPT(1) - nJumpRowUtil
        hasutil = 1
        rstUtil.Close
 
 
'==================================================================================================
'==================================================================================================
NoUtil:
        
        
        .MoveNext
        If hasutil = 1 Then
            TblPT(1) = TblPT(1)
        Else
            TblPT(1) = TblPT(1) - nJumpRow
        End If
        
    Next i
End With

frmSched_CSI.Hide

End Sub

Public Sub FIXTUREFOOD()

'**************************************************************
'**************************************************************
'* MOD 3/7/13 FOR PRFX NOTE
'*
'*
'**************************************************************
'**************************************************************

Dim DB As Database
Dim RstFix As Recordset
Dim strFix As String
Dim rcFix, iatFix, iatType As Integer
Dim TblPT(0 To 2) As Double
Dim tblPT2(0 To 2) As Double
Dim tblWidth As Double
Dim txtHt As Double
Dim textObj As AcadText
Dim attributeObj As AcadAttribute
Dim height As Double
Dim mode As Long
Dim nHeadDwg, nRowDwg As Variant
Dim nJumpHead, nJumpRow As Integer
'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

'Dim oSset As AcadSelectionSet



Set DB = OpenDatabase("\\jwja-svr-10\jdb\db_FIX\X-FIXTURE_17_01.mdb")
'*************************************************************************************************************
'strFix = "SELECT FIXITEM.FXTYPE, PROFIX.PFXID, FIXITEM.FXID, PROFIX.PFXNO, PROFIX.PROJ_NO, PROFIX.PFXRM, " _
& "PROFIX.Pfxnote, FIXITEM.FXSUPPLIER, FIXITEM.FXMODEL, FIXITEM.FXCAT, FIXITEM.FXCOLOR, FIXITEM.FXLISTPRICE, " _
& "PROFIX.FXDISCOUNT, PROFIX.FXPRICE, PROFIX.FXTAX, FIXITEM.FXLEAD, FIXITEM.fxnote, PROFIX.FXQTY, PROFIX.FXPRNOTE, " _
& "Contact.COMPANY, Contact_1.COMPANY, FIXITEM.FXIMGNAME, Contact.RELATION, Contact.LAST, Contact.FIRST, " _
& "Contact.TEL_BUS, Contact.TEL_FAX, Contact.EMAIL, Contact.STREET, Contact.CITY, Contact.STATE, Contact.ZIP, " _
& "Contact_1.RELATION, Contact_1.LAST, Contact_1.FIRST, Contact_1.TITLE, Contact_1.TEL_BUS, Contact_1.TEL_FAX, " _
& "Contact_1.EMAIL, Contact_1.STREET, Contact_1.CITY, Contact_1.STATE, Contact_1.ZIP, PROFIX.FXEXIST, FIXITEM.FXIMGSIM, " _
& "PROFIX.FXPRNOTE, PROFIX.COMMENT, FIXITEM.FXNAME, Trim([CONTACT].[CITY] & ', ' & [CONTACT].[STATE] & ' ' & [CONTACT].[ZIP]) AS SCSZ, " _
& "Trim([CONTACT_1].[CITY] & ', ' & [CONTACT_1].[STATE] & ' ' & [CONTACT_1].[ZIP]) AS MCSZ FROM ((Contact RIGHT JOIN FIXITEM ON Contact.CID = FIXITEM.FXSUPPLIER) " _
& "LEFT JOIN Contact AS Contact_1 ON FIXITEM.FXMFGR = Contact_1.CID) INNER JOIN PROFIX ON FIXITEM.FXID = PROFIX.FXID " _
& "WHERE (((FIXITEM.FXtype) ='" & ListBox2 & "') And ((PROFIX.PROJ_NO) ='" & seleproj & "')) " _
& "ORDER BY PROFIX.PFXNO;"
' THIS OLD
'*************************************************************************************************************









TblPT(0) = 0: TblPT(1) = 0: TblPT(2) = 0
tblPT2(0) = -500: tblPT2(1) = 0: tblPT2(2) = 0
txtHt = 4
txtRow = ""
mode = acAttributeModeVerify
If frmSched_CSI.ShowImage = True Then
    nHeadDwg = "\\jwja-svr-10\drawfile\jvba\XFIXHEAD02.dwg"
    nRowDwg = "\\jwja-svr-10\drawfile\jvba\XFIXROW02.dwg"
    nJumpHead = 60
    nJumpRow = 60
    InsertJBlock "\\jwja-svr-10\drawfile\jvba\XFIXHEAD02.dwg", tblPT2, "Model"
Else
    nHeadDwg = "\\jwja-svr-10\drawfile\jvba\XFIXHEAD01.dwg"
    nRowDwg = "\\jwja-svr-10\drawfile\jvba\XFIXROW01.dwg"
    nJumpHead = 48
    nJumpRow = 24
    InsertJBlock "\\jwja-svr-10\drawfile\jvba\XFIXHEAD01.dwg", tblPT2, "Model"

End If
'ThisDrawing.ModelSpace.InsertBlock tblPT, "H:\drawfile\jvba\XFIXHEAD01.dwg", 1, 1, 1, 0
'InsertJBlock "H:\drawfile\jvba\XDWGTRADE01.dwg", tblPT2, "Model"
'InsertJBlock nHeadDwg, tblPT2, "Model"
'InsertJBlock "e:\drawfile\jvba\XHDWRFOOT02.dwg", tblPT2, "Model"
'tblPT(1) = tblPT(1) - 48

Set RstFix = DB.OpenRecordset(strFix)
RstFix.MoveLast
RstFix.MoveFirst
rcFix = RstFix.RecordCount
Debug.Print rcFix
With RstFix
Set blockRefObj2 = ThisDrawing.ModelSpace.InsertBlock _
                     (TblPT, nHeadDwg, 1, 1, 1, 0)
Dim varAttributes2 As Variant
varAttributes2 = blockRefObj2.GetAttributes
For iatType = LBound(varAttributes2) To UBound(varAttributes2)

Debug.Print varAttributes2(iatType).TagString
    If varAttributes2(iatType).TagString = "XTYPE" Then
        If IsNull(!FXtype) = True Then
            varAttributes2(iatType).textString = ""
        Else
            varAttributes2(iatType).textString = !FXtype & " SCHEDULE"
            Debug.Print varAttributes2(iatType).textString
        End If
    End If
    If varAttributes2(iatType).TagString = "XPROJ_NO" Then
        If IsNull(!PROJ_NO) = True Then
            varAttributes2(iatType).textString = ""
        Else
            varAttributes2(iatType).textString = !PROJ_NO
            Debug.Print varAttributes2(iatType).textString
        End If
    End If
    If varAttributes2(iatType).TagString = "XDATE" Then
        'If IsNull(!fxtype) = True Then
            'varAttributes2(iatType).TextString = ""
        'Else
            varAttributes2(iatType).textString = Date
            Debug.Print varAttributes2(iatType).textString
        'End If
    End If

Next iatType
    TblPT(1) = TblPT(1) - nJumpHead
    For i = 1 To rcFix
        ' xHDWRSETID = !HDWRSETID
        Set blockRefObj = ThisDrawing.ModelSpace.InsertBlock _
                     (TblPT, nRowDwg, 1, 1, 1, 0)
        Dim varAttributes As Variant
        varAttributes = blockRefObj.GetAttributes
    '***************************************************************
    If !FXIMGNAME <> "" Then
    If frmSched_CSI.ShowImage = True Then

    Dim imgPT(0 To 2) As Double
    Dim scalefactor As Double
    Dim rotAngleInDegree As Double, rotAngle As Double
    'Dim imageName As String
    Dim imageName As String

    Dim raster As AcadRasterImage
    Dim imgheight As Variant
    Dim imgwidth As Variant

    'imageName = "C:\AutoCAD\sample\downtown.jpg"
    imageName = !FXIMGNAME
    Debug.Print imageName
    'insertionPoint(0) = 2#: insertionPoint(1) = 2#: insertionPoint(2) = 0#
    imgPT(0) = TblPT(0) + 36: imgPT(1) = TblPT(1) - 54: imgPT(2) = TblPT(2)
    scalefactor = 48#
    'rotAngleInDegree = 0#
    'rotAngle = rotAngleInDegree * 3.141592 / 180#
    rotAngle = 0#
    
    
    
    ' Creates a raster image in model space
    'If !fximgname <> "" Then
    Set raster = ThisDrawing.ModelSpace.AddRaster(imageName, imgPT, scalefactor, rotAngle)
        With raster
        imgheight = raster.ImageHeight
        imgwidth = raster.ImageWidth
            If imgheight > 48 Then
                xSF = (48 / imgheight) * 48
                Debug.Print "xSF: " & xSF * 48
                 raster.scalefactor = xSF
            End If
        End With
    End If
    End If
    '***************************************************************
        For iatFix = LBound(varAttributes) To UBound(varAttributes)
        
        Debug.Print varAttributes(iatFix).TagString
            If varAttributes(iatFix).TagString = "XKEY" Then 'XKEY
                If IsNull(![PFXNO]) = True Then
                    varAttributes(iatFix).textString = ""
                Else
                    varAttributes(iatFix).textString = ![PFXNO]
                    Debug.Print varAttributes(iatFix).textString
                End If
            End If
            If varAttributes(iatFix).TagString = "XMODEL1" Then 'XMODEL1
                If IsNull(!FXMODEL) = True Then
                    varAttributes(iatFix).textString = ""
                Else
                    'varAttributes(iatFix).TextString = SEPTEXT(!FXMODEL, 1, 2, 16)
                    varAttributes(iatFix).textString = SEPTEXT2(!FXMODEL, 1, 2, 16)
                    Debug.Print varAttributes(iatFix).textString
                End If
            End If
            If varAttributes(iatFix).TagString = "XMODEL2" Then 'XMODEL2
                If IsNull(!FXMODEL) = True Then
                    varAttributes(iatFix).textString = ""
                Else
                    'varAttributes(iatFix).TextString = SEPTEXT(!FXMODEL, 2, 2, 16)
                    varAttributes(iatFix).textString = SEPTEXT2(!FXMODEL, 2, 2, 16)
                    Debug.Print varAttributes(iatFix).textString
                End If
            End If
            If varAttributes(iatFix).TagString = "XNAME" Then 'XNAME
                If IsNull(!FXNAME) = True Then
                    varAttributes(iatFix).textString = ""
                Else
                    varAttributes(iatFix).textString = !FXNAME
                    Debug.Print varAttributes(iatFix).textString
                End If
            End If
            If varAttributes(iatFix).TagString = "XCAT" Then 'XCAT
                If IsNull(!FXCAT) = True Then
                    varAttributes(iatFix).textString = ""
                Else
                    varAttributes(iatFix).textString = !FXCAT
                    Debug.Print varAttributes(iatFix).textString
                End If
            End If
            If varAttributes(iatFix).TagString = "XFIN1" Then 'XFIN1
                If IsNull(!FXCOLOR) = True Then
                    varAttributes(iatFix).textString = ""
                Else
                    'varAttributes(iatFix).TextString = SEPTEXT(!FXCOLOR, 1, 2, 7)
                    varAttributes(iatFix).textString = SEPTEXT2(!FXCOLOR, 1, 2, 7)
                    Debug.Print varAttributes(iatFix).textString
                End If
            End If
            If varAttributes(iatFix).TagString = "XFIN2" Then 'XFIN2
                If IsNull(!FXCOLOR) = True Then
                    varAttributes(iatFix).textString = ""
                Else
                    'varAttributes(iatFix).TextString = SEPTEXT(!FXCOLOR, 2, 2, 7)
                    varAttributes(iatFix).textString = SEPTEXT2(!FXCOLOR, 2, 2, 7)
                    Debug.Print varAttributes(iatFix).textString
                End If
            End If
            
            If varAttributes(iatFix).TagString = "XMCOMP" Then 'XMCOMP
                If IsNull(![CONTACT_1.COMPANY]) = True Then
                    varAttributes(iatFix).textString = ""
                Else
                    varAttributes(iatFix).textString = Mid(![CONTACT_1.COMPANY], 1, 26)
                    Debug.Print varAttributes(iatFix).textString
                End If
            End If
            If varAttributes(iatFix).TagString = "XMSTREET" Then 'XMSTREET
                If IsNull(![CONTACT_1.STREET]) = True Then
                    varAttributes(iatFix).textString = ""
                Else
                    varAttributes(iatFix).textString = ![CONTACT_1.STREET]
                    Debug.Print varAttributes(iatFix).textString
                End If
            End If
            If varAttributes(iatFix).TagString = "XMCSZ" Then 'XMCSZ
                If !MCSZ = "," Then
                    varAttributes(iatFix).textString = ""
                Else
                    varAttributes(iatFix).textString = !MCSZ
                    Debug.Print varAttributes(iatFix).textString
                End If
            End If
            If varAttributes(iatFix).TagString = "XMTEL" Then 'XMTEL
                If IsNull(![CONTACT_1.TEL_BUS]) = True Then
                    varAttributes(iatFix).textString = ""
                Else
                    varAttributes(iatFix).textString = Format(![CONTACT_1.TEL_BUS], "###-###-####")
                    Debug.Print varAttributes(iatFix).textString
                End If
            End If
            If varAttributes(iatFix).TagString = "XSCOMP" Then 'XSCOMP
                If IsNull(![CONTACT.COMPANY]) = True Then
                    varAttributes(iatFix).textString = ""
                Else
                    varAttributes(iatFix).textString = Mid(![CONTACT.COMPANY], 1, 26)
                    Debug.Print varAttributes(iatFix).textString
                End If
            End If
            If varAttributes(iatFix).TagString = "XSSTREET" Then 'XSSTREET
                If IsNull(![CONTACT.STREET]) = True Then
                    varAttributes(iatFix).textString = ""
                Else
                    varAttributes(iatFix).textString = ![CONTACT.STREET]
                    Debug.Print varAttributes(iatFix).textString
                End If
            End If
            If varAttributes(iatFix).TagString = "XSCSZ" Then 'XSCSZ
                If !SCSZ = "," Then
                    varAttributes(iatFix).textString = ""
                Else
                    varAttributes(iatFix).textString = !SCSZ
                    Debug.Print varAttributes(iatFix).textString
                End If
            End If
            If varAttributes(iatFix).TagString = "XSTEL" Then 'XSTEL
                If IsNull(![CONTACT.TEL_BUS]) = True Then
                    varAttributes(iatFix).textString = ""
                Else
                    varAttributes(iatFix).textString = Format(![CONTACT.TEL_BUS], "###-###-####")
                    Debug.Print varAttributes(iatFix).textString
                End If
            End If
            If varAttributes(iatFix).TagString = "XNOTE1" Then 'XNOTE1 FXPRNOTE
                If IsNull(!FXPRNOTE) = True Then
                    varAttributes(iatFix).textString = ""
                Else
                    'varAttributes(iatFix).TextString = SEPTEXT(!FXPRNOTE, 1, 3, 16)
                    varAttributes(iatFix).textString = SEPTEXT2(!FXPRNOTE, 1, 3, 16)
                    Debug.Print varAttributes(iatFix).textString
                End If
            End If
            If varAttributes(iatFix).TagString = "XNOTE2" Then 'XNOTE2
                If IsNull(!FXPRNOTE) = True Then
                    varAttributes(iatFix).textString = ""
                Else
                    'varAttributes(iatFix).TextString = SEPTEXT(!FXPRNOTE, 2, 3, 16)
                    varAttributes(iatFix).textString = SEPTEXT2(!FXPRNOTE, 2, 3, 16)
                    Debug.Print varAttributes(iatFix).textString
                End If
            End If
            If varAttributes(iatFix).TagString = "XNOTE3" Then 'XNOTE3
                If IsNull(!FXPRNOTE) = True Then
                    varAttributes(iatFix).textString = ""
                Else
                    'varAttributes(iatFix).TextString = SEPTEXT(!FXPRNOTE, 3, 3, 16)
                    varAttributes(iatFix).textString = SEPTEXT2(!FXPRNOTE, 3, 3, 16)
                    Debug.Print varAttributes(iatFix).textString
                End If
            End If
   '************************************************************************************************
   '************************************************************************************************
            If varAttributes(iatFix).TagString = "XFXNOTE1" Then 'XNOTE3
                If IsNull(!fxnote) = True Then
                    varAttributes(iatFix).textString = ""
                Else
                    varAttributes(iatFix).textString = SEPTEXT2(!fxnote, 1, 3, 16)
                    Debug.Print varAttributes(iatFix).textString
                End If
            End If
            
            If varAttributes(iatFix).TagString = "XFXNOTE2" Then 'XNOTE3
                If IsNull(!fxnote) = True Then
                    varAttributes(iatFix).textString = ""
                Else
                    varAttributes(iatFix).textString = SEPTEXT2(!fxnote, 2, 3, 16)
                    Debug.Print varAttributes(iatFix).textString
                End If
            End If
            
            If varAttributes(iatFix).TagString = "XFXNOTE3" Then 'XNOTE3
                If IsNull(!fxnote) = True Then
                    varAttributes(iatFix).textString = ""
                Else
                    varAttributes(iatFix).textString = SEPTEXT2(!fxnote, 3, 3, 16)
                    Debug.Print varAttributes(iatFix).textString
                End If
            End If
   
   '************************************************************************************************
   '************************************************************************************************
            
            'Dim selectionSet1 As AcadSelectionSet
            'Set selectionSet1 = ThisDrawing.SelectionSets. _
                        Add("NewSelectionSet")

            'ssImg = ThisDrawing.SelectionSets.Item("ImgSet").Add
            'Set rasterObj.Name = ""
            'rasterObj = ThisDrawing.modelspace.ObjectName "cadimg"
            'Set rasterObj.ImageFile = !FXIMGNAME
            
        Next iatFix
        TblPT(1) = TblPT(1) - nJumpRow
        .MoveNext
    Next i
End With

UserForm2.Hide

End Sub

Attribute VB_Name = "Mod_Insp"
Public Sub ShowInsp()
frmInsp.show
End Sub
Public Sub writeInsp()


'############################################################################
'############################################################################
'#         02/13 Working JIN
'#
'#
'#
'#
'#
'############################################################################
'############################################################################

Dim DB As Database
Dim rstProjInsp As Recordset
Dim strProjInsp As String
Dim nInspRow As Integer    'ProjSet no.
Dim iattr_Insp As Integer
'Dim rcArray As Variant
Dim TblPT(0 To 2) As Double
Dim tblPT2(0 To 2) As Double
'Dim tmpArrayAss(0 To 1) As Double

'Dim tblWidth As Double
Dim txtHt As Double
Dim textObj As AcadText
Dim attributeObj As AcadAttribute
'Dim height As Double
'Dim mode As Long
'Dim prompt As String

Dim nInspHeadDwg, nInspRowDwg As Variant
Dim nJumpHead, nJumpRow As Integer
Dim blockRefObj As AcadBlockReference
Dim BlkObj As Object
Dim k, l As Integer


CreateCNstyle
TblPT(0) = 0: TblPT(1) = 0: TblPT(2) = 0
tblPT2(0) = -300: tblPT2(1) = 0: tblPT2(2) = 0
txtHt = 4
txtRow = ""
mode = acAttributeModeVerify

If frmInsp.simplelist = True Then
    nInspHeadDwg = "\\jwja-svr-10\drawfile\jvba\XINSPHEAD01B.dwg"
    nInspRowDwg = "\\jwja-svr-10\drawfile\jvba\XINSPROW01B.dwg"
        
    nJumpHead = 84 '11.5 X 12/ 7x12
    nJumpRow = 24 '3.5 X 12 / 2 x 12
    'InsertJBlock "H:\drawfile\jvba\X_WORKITEM_HEAD02.dwg", tblPT, "Model"
    InsertJBlock "\\jwja-svr-10\drawfile\jvba\XINSPHEAD01B.dwg", TblPT, "Model"
    TblPT(1) = TblPT(1) - nJumpHead

Else
    nInspHeadDwg = "\\jwja-svr-10\drawfile\jvba\X_INSP_HEAD_04.dwg"
    nInspRowDwg = "\\jwja-svr-10\drawfile\jvba\X_INSP_ROW_04.dwg"
        
    nJumpHead = 138 '11.5 X 12
    nJumpRow = 42 '3.5 X 12
    'InsertJBlock "H:\drawfile\jvba\X_WORKITEM_HEAD02.dwg", tblPT, "Model"
    InsertJBlock "\\jwja-svr-10\drawfile\jvba\X_INSP_HEAD_04.dwg", TblPT, "Model"
    TblPT(1) = TblPT(1) - nJumpHead
End If

Set DB = OpenDatabase("\\jwja-svr-10\jdb\db_DOB_INSPECTIONS\X-dob_inspections_01.mdb")

xInspId = frmInsp.seleproj
Debug.Print xInspId
'strProjCode = "SELECT PROJCODE.PROJCODEID, PROJCODE.PROJ_NO, PROJCODE.OCCLOADID, " _
& "Project.PROJ_NAME, Project.PROJ_STNO, Project.PROJ_ADDR, Project.PROJ_CITY, " _
& "Project.PROJ_STATE, Project.PROJ_ZIP, Project.projdesc, Project.PROJ_TYPE, Project.TYPE, " _
& "Project.STATUS, Project.CID, PROJCODE.BLOCK, PROJCODE.LOT, PROJCODE.SECTION, " _
& "PROJCODE.MUNI, PROJCODE.ZONE, PROJCODE.LOTSIZE, PROJCODE.COVERAGE_EXISTING, " _
& "PROJCODE.COVERAGE_NEW, PROJCODE.COMMBD, PROJCODE.BIN, PROJCODE.STORY, PROJCODE.OVZONE, " _
& "PROJCODE.ZONEMAP, PROJCODE.BLDGHT_EX, PROJCODE.BLDGHT_NW, " _
& "Contact.COMPANY, Contact.STREET, Contact.CITY, Contact.STATE, Contact.ZIP, Contact.WEBADDR, Trim([city] & ', ' & [state] & ' ' & [zip]) AS csz " _
& "FROM (PROJCODE INNER JOIN Project ON PROJCODE.PROJ_NO = Project.PROJ_NO) INNER JOIN Contact ON PROJCODE.MUNI = Contact.CID " _
& "WHERE (((PROJCODE.PROJ_NO)='" & xProj_no & "'));"

strProjInsp = "SELECT PROJINSPITEM.proj_no, PROJINSPITEM.projinspid, PROJINSPITEM.INPUT, PROJINSPITEM.INSPNOTE, " _
& "INSPECTION.INSPTYPE, INSPECTION.CODENO, INSPECTION.INSPNAME, INSPECTION.LEADDAYS, PROJINSPITEM.INSTRUCTION " _
& "FROM INSPECTION INNER JOIN PROJINSPITEM ON INSPECTION.INSPID = PROJINSPITEM.INSPID " _
& "WHERE (((PROJINSPITEM.projinspid) = " & xInspId & ")) " _
& "ORDER BY INSPECTION.INSPTYPE, INSPECTION.CODENO;"


Set rstProjInsp = DB.OpenRecordset(strProjInsp)
rstProjInsp.MoveFirst
rstProjInsp.MoveLast
rstProjInsp.MoveFirst
If rstProjInsp.RecordCount = 0 Then
    GoTo Exit_writeINSP
End If
nInspRow = rstProjInsp.RecordCount

With rstProjInsp
    MPROJinspID = !PROJinspID
    For l = 0 To nInspRow - 1
    Set blockRefObj = ThisDrawing.ModelSpace.InsertBlock _
             (TblPT, nInspRowDwg, 1, 1, 1, 0) 'First dwg
             
    Dim varAttributes As Variant
    varAttributes = blockRefObj.GetAttributes
    
    For iattr_Insp = LBound(varAttributes) To UBound(varAttributes)

        Debug.Print varAttributes(iattr_Insp).TagString
'************ XTYPE ***************************************************************
        If varAttributes(iattr_Insp).TagString = "XTYPE" Then
            If IsNull(!INSPTYPE) = True Then
                varAttributes(iattr_Insp).textString = ""
            Else
                varAttributes(iattr_Insp).textString = !INSPTYPE
                Debug.Print varAttributes(iattr_Insp).textString
            End If
        End If
'************ XCODE1 ***************************************************************
        If varAttributes(iattr_Insp).TagString = "XCODE1" Then
            If IsNull(!Codeno) = True Then '++++++++++++++++++++++++++++++++++++++++++
                varAttributes(iattr_Insp).textString = ""
            Else
                varAttributes(iattr_Insp).textString = SEPTEXT2(!Codeno, 1, 2, 16)
                
            End If
        End If
'************ XCODE2 ***************************************************************
        If varAttributes(iattr_Insp).TagString = "XCODE2" Then
            If IsNull(!Codeno) = True Then '++++++++++++++++++++++++++++++++++++++++++
                varAttributes(iattr_Insp).textString = ""
            Else
                varAttributes(iattr_Insp).textString = SEPTEXT2(!Codeno, 2, 2, 16)
                
            End If
        End If
'************ XINSP1 ***************************************************************
        If varAttributes(iattr_Insp).TagString = "XINSP1" Then
            If IsNull(!INSPNAME) = True Then '++++++++++++++++++++++++++++++++++++++++++
                varAttributes(iattr_Insp).textString = ""
            Else
                varAttributes(iattr_Insp).textString = SEPTEXT2(!INSPNAME, 1, 3, 16)
            End If
        End If
'************ XINSP2 ***************************************************************
        If varAttributes(iattr_Insp).TagString = "XINSP2" Then
            If IsNull(!INSPNAME) = True Then '++++++++++++++++++++++++++++++++++++++++++
                varAttributes(iattr_Insp).textString = ""
            Else
                varAttributes(iattr_Insp).textString = SEPTEXT2(!INSPNAME, 2, 3, 16)
            End If
        End If
'************ XINSP3 ***************************************************************
        If varAttributes(iattr_Insp).TagString = "XINSP3" Then
            If IsNull(!INSPNAME) = True Then '++++++++++++++++++++++++++++++++++++++++++
                varAttributes(iattr_Insp).textString = ""
            Else
                varAttributes(iattr_Insp).textString = SEPTEXT2(!INSPNAME, 3, 3, 16)
            End If
        End If
'************ XINST1 ***************************************************************
        If varAttributes(iattr_Insp).TagString = "XINST1" Then
            If IsNull(!INSTRUCTION) = True Then '++++++++++++++++++++++++++++++++++++++++++
                varAttributes(iattr_Insp).textString = ""
            Else
                varAttributes(iattr_Insp).textString = SEPTEXT2(!INSTRUCTION, 1, 6, 64)
            End If
        End If
'************ XINST2 ***************************************************************
        If varAttributes(iattr_Insp).TagString = "XINST2" Then
            If IsNull(!INSTRUCTION) = True Then '++++++++++++++++++++++++++++++++++++++++++
                varAttributes(iattr_Insp).textString = ""
            Else
                varAttributes(iattr_Insp).textString = SEPTEXT2(!INSTRUCTION, 2, 6, 64)
            End If
        End If
'************ XINST3 ***************************************************************
        If varAttributes(iattr_Insp).TagString = "XINST3" Then
            If IsNull(!INSTRUCTION) = True Then '++++++++++++++++++++++++++++++++++++++++++
                varAttributes(iattr_Insp).textString = ""
            Else
                varAttributes(iattr_Insp).textString = SEPTEXT2(!INSTRUCTION, 3, 6, 64)
            End If
        End If
'************ XINST4 ***************************************************************
        If varAttributes(iattr_Insp).TagString = "XINST4" Then
            If IsNull(!INSTRUCTION) = True Then '++++++++++++++++++++++++++++++++++++++++++
                varAttributes(iattr_Insp).textString = ""
            Else
                varAttributes(iattr_Insp).textString = SEPTEXT2(!INSTRUCTION, 4, 6, 64)
            End If
        End If
'************ XINST5 ***************************************************************
        If varAttributes(iattr_Insp).TagString = "XINST5" Then
            If IsNull(!INSTRUCTION) = True Then '++++++++++++++++++++++++++++++++++++++++++
                varAttributes(iattr_Insp).textString = ""
            Else
                varAttributes(iattr_Insp).textString = SEPTEXT2(!INSTRUCTION, 5, 6, 64)
            End If
        End If
'************ XINST6 ***************************************************************
        If varAttributes(iattr_Insp).TagString = "XINST6" Then
            If IsNull(!INSTRUCTION) = True Then '++++++++++++++++++++++++++++++++++++++++++
                varAttributes(iattr_Insp).textString = ""
            Else
                varAttributes(iattr_Insp).textString = SEPTEXT2(!INSTRUCTION, 6, 6, 64)
            End If
        End If
'************ XLEAD ***************************************************************
        If varAttributes(iattr_Insp).TagString = "XLEAD" Then
            If IsNull(!LEADDAYS) = True Then '++++++++++++++++++++++++++++++++++++++++++
                varAttributes(iattr_Insp).textString = ""
            Else
                varAttributes(iattr_Insp).textString = !LEADDAYS
            End If
        End If
'************ XNOTE1 ***************************************************************
        If varAttributes(iattr_Insp).TagString = "XNOTE1" Then
            If IsNull(!INSPNOTE) = True Then '++++++++++++++++++++++++++++++++++++++++++
                varAttributes(iattr_Insp).textString = ""
            Else
                varAttributes(iattr_Insp).textString = SEPTEXT2(!INSPNOTE, 1, 4, 36)
            End If
        End If
'************ XNOTE2 ***************************************************************
        If varAttributes(iattr_Insp).TagString = "XNOTE2" Then
            If IsNull(!INSPNOTE) = True Then '++++++++++++++++++++++++++++++++++++++++++
                varAttributes(iattr_Insp).textString = ""
            Else
                varAttributes(iattr_Insp).textString = SEPTEXT2(!INSPNOTE, 2, 4, 36)
            End If
        End If
'************ XNOTE3 ***************************************************************
        If varAttributes(iattr_Insp).TagString = "XNOTE3" Then
            If IsNull(!INSPNOTE) = True Then '++++++++++++++++++++++++++++++++++++++++++
                varAttributes(iattr_Insp).textString = ""
            Else
                varAttributes(iattr_Insp).textString = SEPTEXT2(!INSPNOTE, 3, 4, 36)
            End If
        End If
'************ XNOTE4 ***************************************************************
        If varAttributes(iattr_Insp).TagString = "XNOTE4" Then
            If IsNull(!INSPNOTE) = True Then '++++++++++++++++++++++++++++++++++++++++++
                varAttributes(iattr_Insp).textString = ""
            Else
                varAttributes(iattr_Insp).textString = SEPTEXT2(!INSPNOTE, 4, 4, 36)
            End If
        End If

'************ END TEXT INSERT LOOP ***************************************************************

    Next iattr_Insp
     TblPT(1) = TblPT(1) - nJumpRow
    .MoveNext
        
    Next l
   rstProjInsp.Close
End With

Set DB = Nothing

Exit_writeINSP:
frmInsp.Hide
End Sub

Attribute VB_Name = "Mod_ProjCode"

Public Sub ShowProjCode()
frmProjCode.show
End Sub

'**********************************************************************************************************
'**********************************************************************************************************
'**********************************************************************************************************
'*********************** 9/23/18 ***************************************************
'**********************************************************************************************************
'**********************************************************************************************************
'**********************************************************************************************************
'**********************************************************************************************************


Function writeProjCodeNW(xProjCodeID, xChapterID As Integer)
'On Error GoTo Err_writemtext
Dim DB As Database
Dim rstChapter, rstSection, rstSubSection As Recordset
Dim strChapter, strSection, strSubSection, CodeText As String
Dim rnChapter, rnSection, rnSubSection, rnCodePara1 As Integer
Dim iChapter, iSection, iSubSection, iCodePara1 As Integer
Dim CodeArray() As Variant
Dim StartPoint(0 To 2) As Double
Dim SectionPoint(0 To 2) As Double
Dim paraPoint(0 To 2) As Double
Dim TextPosition(0 To 2) As Double
Dim TblPT(0 To 2) As Double
Dim TblEndPT(0 To 2) As Double
Dim SizestartPoint(0 To 2) As Double
Dim width As Double
Dim mATno As Integer
Dim tmpCodeText As String


'*********************************************************************************************
'*********************************************************************************************
Set DB = OpenDatabase("\\jwja-svr-10\jdb\DB_CODE\2018-Code-01.mdb")
'*********************************************************************************************
'*********************************************************************************************
' 09/22/18
'*********************************************************************************************
'*********************************************************************************************
'mSCF= Scale Factor
If frmProjCode.OptionButton1.value Then
    mSCF = 48 'mSCF= Scale Factor
    'width = mSCF * 8 '48 x 8 = 384
    width = mSCF * 7 '48 x 7 = 336
    xScF = mSCF / 12


ElseIf frmProjCode.OptionButton2.value Then
    mSCF = 96
    width = mSCF * 7 '96 x 8 = 768
    xScF = mSCF / 12
    xScFBig = xScF * 1.5
ElseIf frmProjCode.OptionButton3.value Then
    mSCF = 64
    width = mSCF * 7 '64 x 8 = 512
    xScF = mSCF / 12
ElseIf frmProjCode.OptionButton4.value Then
    mSCF = 128
    width = mSCF * 7 '64 x 8 = 512
    xScF = mSCF / 12
ElseIf frmProjCode.OptionButton5.value Then
    mSCF = 192
    width = mSCF * 7 '64 x 8 = 512
    xScF = mSCF / 12

End If
xScFBig = xScF * 1.5


    'mSCF = 48 'mSCF= Scale Factor
    'width = mSCF * 8 '48 x 8 = 384
    'width = 1440 * 6

'*********************************************************************************************
'*********************************************************************************************
'startPoint(0) = 0#: startPoint(1) = 0#: startPoint(2) = 0#
SectionPoint(0) = 0#: SectionPoint(1) = 0#: SectionPoint(2) = 0#
paraPoint(0) = 0#: paraPoint(1) = 0#: paraPoint(2) = 0#
TextPosition(0) = 0#: TextPosition(1) = 0#: TextPosition(2) = 0#
'width = 384 '32' X 12'

CodeText = ""
mChapterNo = 1
'**********************************************************************************************************
'**********************************************************************************************************

'strPCSI = "SELECT PROJCSI.PROJCSIID, PROJCSI.PROJCSIDATE, PROJCSI.PROJSPECID, " _
& "PROJCSI.PROJ_NO, MCSI.MCSIID, MCSI.MCSI, MCSI.MCSINAME " _
& "FROM MCSI INNER JOIN PROJCSI ON MCSI.MCSIID = PROJCSI.MCSIID " _
& "WHERE (((PROJCSI.PROJCSIID)=" & xProjCSIID & "));"

strChapter = "SELECT rellaw.projcodeid, rellaw.chapterid, chapter.chapterno, chapter.chaptername, chapter.codeid " _
& "FROM rellaw INNER JOIN chapter ON rellaw.chapterid = chapter.chapterID " _
& "WHERE (((rellaw.projcodeid)=" & xProjCodeID & ") AND ((rellaw.chapterid)=" & xChapterID & "));"



Set rstChapter = DB.OpenRecordset(strChapter)
rnChapter = rstChapter.RecordCount

'=============================================================
' With 01
'=============================================================
With rstChapter
'=============================================================
' Loop 01
'=============================================================

For iChapter = 1 To rnChapter
    Debug.Print "xChapterID : " & xChapterID
    '*********************** Format Start CSIName ************************************************
    If frmProjCode!mNote = True Then
    '*********************************************************************************************************
        '*********************************************************************************************************
        'text = text & Chr(10) & "\Farial.ttf;\H8.0;" & RsCSI!mCSI & " " & RsCSI!MCSIname & "\P"
        '*********************************************************************************************************
        text = text & Chr(10) & "\Farial.ttf;\H" & xScFBig & ";" & rstChapter!chapterno & " " & rstChapter!chaptername & " " & rstChapter!chapterid & "\P"
        '*********************************************************************************************************
        '*********************************************************************************************************
    Else
        'text = text & Chr(10) & RsCSI!mCSI & " " & RsCSI!MCSIname & "\P"
        'codetext = codetext & Chr(10) & rstChapter!chapterno & " " & rstChapter!chaptername & " " & rstChapter!chapterid & "\P"
        'codetext = Chr(10) & rstChapter!chapterno & " " & rstChapter!chaptername & "\P"
        CodeText = Chr(10) & "\Farial.ttf;\H" & xScFBig & ";" & rstChapter!chapterno & " - " & rstChapter!chaptername & "\P"
    End If
    '=================================================================================================================================
    '#############################
    '=================================================================================================================================
    '######### Write Chapter
    '=================================================================================================================================
    TextPosition(0) = 0#: TextPosition(1) = 0#: TextPosition(2) = 0#
    Set mtextObj = ThisDrawing.ModelSpace.AddMText(TextPosition, width, CodeText)
    mtextObj.Update
    mtextObj.GetBoundingBox minText, maxText
    TextPosition(1) = minText(1) + TextPosition(1)
    TextPosition(0) = TextPosition(0) - 12
    strTextPosition = "Chapter X: " & TextPosition(0) & " Y: " & TextPosition(1)
    'Set mPositionObj = ThisDrawing.ModelSpace.AddMText(TextPosition, width, strTextPosition)
    'mPositionObj.Update
    TextPosition(0) = 0#
    '=================================================================================================================================
    '######### Write Chapter End
    '=================================================================================================================================
    '=================================================================================================================================
    
    '*********************** Format End CSIName ************************************************
    '=================================================================================================================================
    '=================================================================================================================================
    ' Related Section
    '=================================================================================================================================
    '=================================================================================================================================
    'strSection_01 = "SELECT rellaw.sectionid, section.sectionno, section.section, section.articleid, " _
    & "rellaw.relLawId, rellaw.tblName, rellaw.codeid, rellaw.chapterid, rellaw.subsectionid, rellaw.paraid, rellaw.lawno, rellaw.rellawmemo, rellaw.input, rellaw.projcodeid, rellaw.chapterno, Val([sectionno]) AS vSectionNo " _
    & "FROM [section] INNER JOIN rellaw ON section.sectionid = rellaw.sectionid " _
    & "WHERE (((rellaw.chapterid) =" & xChapterID & ") And ((rellaw.projcodeid) =" & xProjCodeid & ")) " _
    & "ORDER BY Val([sectionno]),rellaw.lawno;"
    
    strSection = "SELECT section.sectionno, section.section, section.sectionid, Val([sectionno]) AS vSectionNo, rellaw.projcodeid, rellaw.chapterid " _
    & "FROM [section] INNER JOIN rellaw ON section.sectionid = rellaw.sectionid " _
    & "GROUP BY section.sectionno, section.section, section.sectionid, Val([sectionno]), rellaw.projcodeid, rellaw.chapterid " _
    & "HAVING (((rellaw.projcodeid) = " & xProjCodeID & ") And ((rellaw.chapterid) = " & xChapterID & ")) " _
    & "ORDER BY Val([sectionno]);"


    '=================================================================================================================================
    Set rstSection = DB.OpenRecordset(strSection)
    '=============================================================
    ' With 02
    '=============================================================
    With rstSection
    .MoveFirst
    .MoveLast
    .MoveFirst
    rnSection = rstSection.RecordCount
    Debug.Print "rnSection: " & rnSection
    If rnSection > 0 Then
        Debug.Print "rnSection: " & rnSection
    End If
    '=============================================================
    ' Loop 02 Section
    '=============================================================
    For iSection = 1 To rnSection
        If frmProjCode!mNote = True Then
            
            'text = text & "\P" & Chr(9) & RsPart!MPART & "\P"
            Debug.Print rstSection!section
            CodeText = CodeText
        Else
            'codetext = codetext & "\P" & "Section " & rstSection!sectionno & Chr(9) & rstSection!section & "\P"
            'Set MTextObj = ThisDrawing.ModelSpace.AddMText(corner, width, text)
            CodeText = "Section " & rstSection!sectionno & Chr(9) & rstSection!section & "\P"
        End If
        '=================================================================================================================================
        '######### Write Section
        '=================================================================================================================================
        Set mtextObj = ThisDrawing.ModelSpace.AddMText(TextPosition, width, CodeText)
        If frmProjCode!mNote = True Then
            CreateARstyle
            mtextObj.StyleName = "ar"
            mtextObj.height = xScF
        Else
            CreateCNstyle
            mtextObj.StyleName = "cn"
            mtextObj.height = xScF
        End If
        mtextObj.Update
        mtextObj.GetBoundingBox minText, maxText
        'TextPosition(1) = minText(1) + TextPosition(1)
        TextPosition(1) = minText(1)
        strTextPosition = "Section X: " & TextPosition(0) & "Y: " & TextPosition(1) + 8
        'Set mPositionObj = ThisDrawing.ModelSpace.AddMText(TextPosition, width, strTextPosition)
        'mPositionObj.Update
        '=================================================================================================================================
        '######### Write Section End
        '=================================================================================================================================
        '<<<<<<<<<<<<<<<<<<<<<<<<<<<<<<<<<<<<<<<<<<<<<<<<<<<<<<<<<<<<<<<<<<<<<<<<<<<<<<<<<<<<<<<<<<<
        xSectionId = rstSection!sectionid
        
        '=================================================================================================================================
        '=================================================================================================================================
        ' Related CodePara
        '=================================================================================================================================
        '=================================================================================================================================
        CodeText = ""
        strCodePara = " SELECT rellaw.lawno, rellaw.relLawId, rellaw.tblName, rellaw.codeid, rellaw.chapterid, rellaw.sectionid, rellaw.subsectionid, " _
        & "rellaw.paraid, rellaw.rellawmemo, rellaw.input, rellaw.projcodeid, rellaw.sectionid " _
        & "FROM rellaw " _
        & "WHERE (((rellaw.projcodeid) = " & xProjCodeID & ") And ((rellaw.sectionid) = " & xSectionId & ")) " _
        & "ORDER BY rellaw.lawno;"
        Set rstCodePara = DB.OpenRecordset(strCodePara)
        '=============================================================
        ' Loop 03 Para
        '=============================================================
        Do While Not rstCodePara.EOF
        Debug.Print rstCodePara!rellawmemo
        'codetext = codetext & "\P" & rstCodePara!lawno & Chr(9) & rstCodePara!tblname & Chr(9) & rstCodePara!paraid & "\P"
        Select Case rstCodePara!tblName
        '+++++++++++++++++++++++++++++++++++++++++++++
        '********************** Problem Here!!! ******************
        
        Case "subsection"
        
            'strCodeText = "SELECT Val([subsectionno]) AS Expr1, subsection.lawno, rellaw.projcodeid, rellaw.tblname, rellaw.paraid, subsection.sectionid, subsection.subsection, subsection.subsectionid " _
            & "FROM subsection INNER JOIN rellaw ON subsection.subsectionid = rellaw.subsectionid " _
            & "GROUP BY Val([subsectionno]), subsection.lawno, rellaw.projcodeid, rellaw.tblname, rellaw.paraid, subsection.sectionid, subsection.subsection, subsection.subsectionid " _
            & "HAVING (((rellaw.projcodeid) = " & xProjCodeID & ") And ((subsection.sectionid) = " & xSectionId & ")) " _
            & "ORDER BY Val([subsectionno]), subsection.lawno;"
            '****************Corrected below 18/11/11
            'strCodeText_old = "SELECT subsection.lawno, subsection.subsectionid, subsection.subsectionno, subsection.subsection, subsection.sectionid " _
            & "FROM subsection " _
            & "GROUP BY subsection.lawno, subsection.subsectionid, subsection.subsectionno, subsection.subsection, subsection.sectionid " _
            & "HAVING (((subsection.subsectionid) = " & rstCodePara!paraid & ")) " _
            & "ORDER BY subsection.lawno;"
            
            strCodeText = "SELECT subsection.lawno, subsection.subsectionid, subsection.subsectionno, subsection.subsection, subsection.sectionid " _
            & "FROM subsection " _
            & "where (((subsection.subsectionid) = " & rstCodePara!paraid & ")) " _
            & "ORDER BY subsection.lawno;"
            'test 551
            
            Set rstCodeText = DB.OpenRecordset(strCodeText)
            rnrstCodeText = rstCodeText.RecordCount
            If (rnrstCodeText) = 0 Then
            
            GoTo EndselectPara
            Else
            tmpCodeText = rstCodeText!subsection
            End If
            Debug.Print rstCodeText!subsection
            tmpException = writeException(xProjCodeID, "subsection", rstCodeText!subsectionid)
            Debug.Print tmpCodeText
            tmpMemo = ""
            Debug.Print rstCodePara!rellawmemo
            If IsNull(rstCodePara!rellawmemo) = False Then

            tmpMemo = rstCodePara!rellawmemo
            End If
            
            rstCodeText.Close
            Set rstCodeText = Nothing
        '+++++++++++++++++++++++++++++++++++++++++++++
        Case "codepara1"
            'codetext = codetext & "\P" & "xxxPara1" & "\P"
            strCodeText = "SELECT codepara1.codepara1id, codepara1.codepara1no, codepara1.lawno, codepara1.codepara1 " _
            & "FROM codepara1 " _
            & "WHERE (((codepara1.codepara1id) =" & rstCodePara!paraid & ")) " _
            & "ORDER BY codepara1.lawno;"
            Set rstCodeText = DB.OpenRecordset(strCodeText)
            'Do While Not rstCodeText.EOF
            tmpCodeText = rstCodeText!codepara1
            tmpMemo = ""
            If IsNull(rstCodePara!rellawmemo) = False Then
            tmpMemo = rstCodePara!rellawmemo
            End If
            
            rstCodeText.Close
            Set rstCodeText = Nothing
            'Loop
        Case "codepara2"
            'codetext = codetext & "\P" & "xxxPara2" & "\P"
            strCodeText = "SELECT codepara2.codepara2id, codepara2.codepara2no, codepara2.lawno, codepara2.codepara2 " _
            & "FROM codepara2 " _
            & "WHERE (((codepara2.codepara2id) =" & rstCodePara!paraid & ")) " _
            & "ORDER BY codepara2.lawno;"
            Set rstCodeText = DB.OpenRecordset(strCodeText)
            'Do While Not rstCodeText.EOF
            tmpCodeText = rstCodeText!codepara2
            tmpMemo = ""
    
            If IsNull(rstCodePara!rellawmemo) = False Then
            tmpMemo = rstCodePara!rellawmemo
            End If
            rstCodeText.Close
            Set rstCodeText = Nothing
        
        Case "codepara3"
            'codetext = codetext & "\P" & "xxxPara3" & "\P"
            strCodeText = "SELECT codepara3.codepara3id, codepara3.codepara3no, codepara3.lawno, codepara3.codepara3 " _
            & "FROM codepara3 " _
            & "WHERE (((codepara3.codepara3id) =" & rstCodePara!paraid & ")) " _
            & "ORDER BY codepara3.lawno;"
            Set rstCodeText = DB.OpenRecordset(strCodeText)
            'Do While Not rstCodeText.EOF
            tmpCodeText = rstCodeText!codepara3
            tmpMemo = ""
            If IsNull(rstCodePara!rellawmemo) = False Then
            tmpMemo = rstCodePara!rellawmemo
            End If
            rstCodeText.Close
            Set rstCodeText = Nothing
        
        Case "codeepara4"
            'codetext = codetext & "\P" & "xxxPara4" & "\P"
            strCodeText = "SELECT codepara4.codepara4id, codepara4.codepara4no, codepara4.lawno, codepara4.codepara4 " _
            & "FROM codepara4 " _
            & "WHERE (((codepara4.codepara4id) =" & rstCodePara!paraid & ")) " _
            & "ORDER BY codepara4.lawno;"
            Set rstCodeText = DB.OpenRecordset(strCodeText)
            'Do While Not rstCodeText.EOF
            tmpCodeText = rstCodeText!codepara4
            tmpMemo = ""
            If IsNull(rstCodePara!rellawmemo) = False Then
            tmpMemo = rstCodePara!rellawmemo
            End If
            rstCodeText.Close
            Set rstCodeText = Nothing
        Case "exception"
            'codetext = codetext & "\P" & "xxxPara4" & "\P"
             strCodeText = "SELECT exception.exceptionid, exception.exceptionno, exception.exception, exception.codepara1id, exception.codepara2id, exception.lawno, exception.subsectionid, exception.sectionid, exception.tblname, exception.paraid, exception.codeid " _
            & "FROM [exception] " _
            & "WHERE (((exception.exceptionid) =" & rstCodePara!paraid & ")) " _

            
            Set rstCodeText = DB.OpenRecordset(strCodeText)
            'Do While Not rstCodeText.EOF
            tmpCodeText = rstCodeText!exception
            tmpMemo = ""
            If IsNull(rstCodePara!rellawmemo) = False Then
            tmpMemo = rstCodePara!rellawmemo
            End If
            rstCodeText.Close
            Set rstCodeText = Nothing
            'exception
EndselectPara:
        End Select
    '=================================================================================================================================
    '######### Write Para
    '=================================================================================================================================
    If (tmpMemo) = "" Then
        CodeText = CodeText & "\P" & rstCodePara!lawno & Chr(9) & tmpCodeText & "\P"
    Else
        'codetext = codetext & "\P" & rstCodePara!lawno & Chr(9) & tmpCodeText & "\P" & "\P" & BigText(tmpMemo) & "\P"
        CodeText = CodeText & "\P" & rstCodePara!lawno & Chr(9) & tmpCodeText & "\P"
        'TblPT(0) = mTab + TextPosition(0)
        'TblEndPT(0) = TblPT(0) + 32
        'ThisDrawing.ModelSpace.AddLine TblPT, TblEndPT
        'codetext = codetext & "\P" & BigText(tmpMemo) & "\P"
        
    End If
    'tmpMemo = ""
    
    'startPoint(0) = 0#: startPoint(1) = 0#: startPoint(2) = 0#
    '1440 x 0.5 = 720
    mTab = 12
    TextPosition(0) = mTab + TextPosition(0)
    Set mtextObj = ThisDrawing.ModelSpace.AddMText(TextPosition, width, CodeText)
    If frmProjCode!mNote = True Then
        CreateARstyle
        mtextObj.StyleName = "ar"
        mtextObj.height = xScF
    Else
        CreateCNstyle
        mtextObj.StyleName = "cn"
        mtextObj.height = xScF
    End If

    mtextObj.Update
    mtextObj.GetBoundingBox minText, maxText
    TextPosition(1) = minText(1)
    If (tmpMemo) = "" Then
    Else
        'width = 384 '32' X 12'
        TblPT(0) = mTab + mTab + TextPosition(0)
        TblPT(1) = TextPosition(1)
        TblEndPT(0) = TblPT(0) + (width - TblPT(0))
        TblEndPT(1) = TextPosition(1)
        ThisDrawing.ModelSpace.AddLine TblPT, TblEndPT
        
        codeMemo = "\P" & BigText("Project Note: " & tmpMemo, xScFBig) & "\P"
         TextPosition(0) = mTab + mTab + TextPosition(0)
        Set mtextObj = ThisDrawing.ModelSpace.AddMText(TextPosition, width, codeMemo)
        TextPosition(0) = TextPosition(0) - mTab - mTab
        mtextObj.StyleName = "a"
        mtextObj.height = xScF
        mtextObj.Update
        
       
        mtextObj.GetBoundingBox minText, maxText
        TextPosition(1) = minText(1)
        TblPT(0) = mTab + mTab + TextPosition(0)
        TblPT(1) = TextPosition(1)
        TblEndPT(0) = TblPT(0) + (width - TblPT(0))
        TblEndPT(1) = TextPosition(1)
        ThisDrawing.ModelSpace.AddLine TblPT, TblEndPT
    End If
    tmpMemo = ""

    
    
    TextPosition(0) = 0#
    'TextPosition(1) = minText(1) + TextPosition(1)
    TextPosition(1) = minText(1)
    
    strTextPosition = "Section X: " & TextPosition(0) & "Y: " & TextPosition(1)
    'Set mPositionObj = ThisDrawing.ModelSpace.AddMText(TextPosition, width, strTextPosition)
    'mPositionObj.Update
    CodeText = ""
    '=================================================================================================================================
    '######### Write Para End
    '=================================================================================================================================
nextiPara:
        rstCodePara.MoveNext
        Loop
        '=============================================================
        ' Loop 03 Para End
        '=============================================================
End03:
               
        rstCodePara.Close
        Set rstCodePara = Nothing
    '-----------------------------------------------------------------------------------------------------
    
    '>>>>>>>>>>>>>>>>>>>>>>>>>>>>>>>>>>>>>>>>>>>>>>>>>>>>>>>>>>>>>>>>>>>>>>>>>>>>>>>>>>>>>>>>>>>>>>
    '>>>>>>>>>>>>>>>>>>>>>>>>>>>>>>>>>>>>>>>>>>>>>>>>>>>>>>>>>>>>>>>>>>>>>>>>>>>>>>>>>>>>>>>>>>>>>>
    '>>>>>>>>>>>>>>>>>>>>>>>>>>>>>>>>>>>>>>>>>>>>>>>>>>>>>>>>>>>>>>>>>>>>>>>>>>>>>>>>>>>>>>>>>>>>>>
    
'=============================================================
' Loop 02 Section end
'=============================================================
    rstSection.MoveNext
    Next iSection
    End With
    rstSection.Close
'rstChapter.MoveNext
'=============================================================
' Loop 01 end
'=============================================================
Next iChapter
                'rstSubSection.Close
               ' Set rstSubSection = Nothing
                'rstCodePara1.Close
                'Set rstCodePara1 = Nothing
                'rstCodePara2.Close
                'Set rstCodePara2 = Nothing
                'rstCodePara3.Close
                'Set rstCodePara3 = Nothing
                
                
'Set mtextObj = ThisDrawing.ModelSpace.AddMText(startPoint, width, codetext)
'mtextObj.Update
End With
'=============================================================
'With 01 End
'=============================================================
rstChapter.Close

Set rstChapter = Nothing
DB.Close
'mtextObj.GetBoundingBox minExt, maxExt
'SizestartPoint(0) = 0#: SizestartPoint(1) = minExt(1) + 0#: SizestartPoint(2) = 0#
'textobjSize = "minExt: " & minExt(1) & " maxExt: " & maxExt(1)
'Set mtextobjsize = ThisDrawing.ModelSpace.AddMText(SizestartPoint, width, textobjSize)
'mtextobjsize.Update

Debug.Print rnPart & rnAt & rnPara1
       
End Function
'**********************************************************************************************************
'**********************************************************************************************************
'**********************************************************************************************************
'**********************************************************************************************************
'**********************************************************************************************************
'**********************************************************************************************************
'**********************************************************************************************************
'**********************************************************************************************************
'**********************************************************************************************************
'**********************************************************************************************************
Function writeProjCode(xProjCodeID, xChapterID As Integer)
'On Error GoTo Err_writemtext
Dim DB As Database
Dim rstChapter, rstSection, rstSubSection As Recordset
Dim strChapter, strSection, strSubSection, CodeText As String
Dim rnChapter, rnSection, rnSubSection, rnCodePara1 As Integer
Dim iChapter, iSection, iSubSection, iCodePara1 As Integer
Dim CodeArray() As Variant
Dim StartPoint(0 To 2) As Double
Dim SectionPoint(0 To 2) As Double
Dim paraPoint(0 To 2) As Double
Dim TextPosition(0 To 2) As Double
Dim TblPT(0 To 2) As Double
Dim TblEndPT(0 To 2) As Double
Dim SizestartPoint(0 To 2) As Double
Dim width As Double
Dim mATno As Integer


'**********************************************************************************************************
'**********************************************************************************************************
Set DB = OpenDatabase("\\jwja-svr-10\jdb\DB_CODE\2018-Code-01.mdb")


'*********************************************************************************************
'*********************************************************************************************
' 09/22/18
'*********************************************************************************************
'*********************************************************************************************
'mSCF= Scale Factor
If frmProjCode.OptionButton1.value Then
    mSCF = 48 'mSCF= Scale Factor
    width = mSCF * 8 '48 x 8 = 384
ElseIf frmProjCode.OptionButton2.value Then
    mSCF = 96
    width = mSCF * 8 '96 x 8 = 768
ElseIf frmProjCode.OptionButton3.value Then
    mSCF = 64
    width = mSCF * 8 '64 x 8 = 512
End If

xScF8 = mSCF / 12 * 2
xScF6 = mSCF / 12 * 1.5
xScF4 = mSCF / 12 * 1
    'mSCF = 48 'mSCF= Scale Factor
    'width = mSCF * 8 '48 x 8 = 384
    'width = 1440 * 6
    If frmProjCode!mNote = True Then
        CreateARstyle
        mtextObj.StyleName = "ar"
        mtextObj.height = 4
    Else
        CreateCNstyle
        mtextObj.StyleName = "cn"
        mtextObj.height = 4
    End If
'*********************************************************************************************
'*********************************************************************************************
'startPoint(0) = 0#: startPoint(1) = 0#: startPoint(2) = 0#
SectionPoint(0) = 0#: SectionPoint(1) = 0#: SectionPoint(2) = 0#
paraPoint(0) = 0#: paraPoint(1) = 0#: paraPoint(2) = 0#
TextPosition(0) = 0#: TextPosition(1) = 0#: TextPosition(2) = 0#
width = 384 '32' X 12'

CodeText = ""
mChapterNo = 1
'**********************************************************************************************************
'**********************************************************************************************************

'strPCSI = "SELECT PROJCSI.PROJCSIID, PROJCSI.PROJCSIDATE, PROJCSI.PROJSPECID, " _
& "PROJCSI.PROJ_NO, MCSI.MCSIID, MCSI.MCSI, MCSI.MCSINAME " _
& "FROM MCSI INNER JOIN PROJCSI ON MCSI.MCSIID = PROJCSI.MCSIID " _
& "WHERE (((PROJCSI.PROJCSIID)=" & xProjCSIID & "));"

strChapter = "SELECT rellaw.projcodeid, rellaw.chapterid, chapter.chapterno, chapter.chaptername, chapter.codeid " _
& "FROM rellaw INNER JOIN chapter ON rellaw.chapterid = chapter.chapterID " _
& "WHERE (((rellaw.projcodeid)=" & xProjCodeID & ") AND ((rellaw.chapterid)=" & xChapterID & "));"



Set rstChapter = DB.OpenRecordset(strChapter)
rnChapter = rstChapter.RecordCount

'=============================================================
' With 01
'=============================================================
With rstChapter
'=============================================================
' Loop 01
'=============================================================

For iChapter = 1 To rnChapter
    Debug.Print "xChapterID : " & xChapterID
    '*********************** Format Start CSIName ************************************************
    If frmProjCode!mNote = True Then
    '*********************************************************************************************************
        '*********************************************************************************************************
        'text = text & Chr(10) & "\Farial.ttf;\H8.0;" & RsCSI!mCSI & " " & RsCSI!MCSIname & "\P"
        '*********************************************************************************************************
        text = text & Chr(10) & "\Farial.ttf;\H" & xScF8 & ";" & rstChapter!chapterno & " " & rstChapter!chaptername & " " & rstChapter!chapterid & "\P"
        '*********************************************************************************************************
        '*********************************************************************************************************
    Else
        'text = text & Chr(10) & RsCSI!mCSI & " " & RsCSI!MCSIname & "\P"
        'codetext = codetext & Chr(10) & rstChapter!chapterno & " " & rstChapter!chaptername & " " & rstChapter!chapterid & "\P"
        CodeText = Chr(10) & rstChapter!chapterno & " " & rstChapter!chaptername & " <" & rstChapter!chapterid & "> \P"
    End If
    '=================================================================================================================================
    '#############################
    '=================================================================================================================================
    '######### Write Chapter
    '=================================================================================================================================
    TextPosition(0) = 0#: TextPosition(1) = 0#: TextPosition(2) = 0#
    Set mtextObj = ThisDrawing.ModelSpace.AddMText(TextPosition, width, CodeText)
    mtextObj.Update
    mtextObj.GetBoundingBox minText, maxText
    TextPosition(1) = minText(1) + TextPosition(1)
    TextPosition(0) = TextPosition(0) - 12
    strTextPosition = "Chapter X: " & TextPosition(0) & " Y: " & TextPosition(1)
    Set mPositionObj = ThisDrawing.ModelSpace.AddMText(TextPosition, width, strTextPosition)
    mPositionObj.Update
    TextPosition(0) = 0#
    '=================================================================================================================================
    '######### Write Chapter End
    '=================================================================================================================================
    '=================================================================================================================================
    
    '*********************** Format End CSIName ************************************************
    '=================================================================================================================================
    '=================================================================================================================================
    ' Related Section
    '=================================================================================================================================
    '=================================================================================================================================
    'strSection_01 = "SELECT rellaw.sectionid, section.sectionno, section.section, section.articleid, " _
    & "rellaw.relLawId, rellaw.tblName, rellaw.codeid, rellaw.chapterid, rellaw.subsectionid, rellaw.paraid, rellaw.lawno, rellaw.rellawmemo, rellaw.input, rellaw.projcodeid, rellaw.chapterno, Val([sectionno]) AS vSectionNo " _
    & "FROM [section] INNER JOIN rellaw ON section.sectionid = rellaw.sectionid " _
    & "WHERE (((rellaw.chapterid) =" & xChapterID & ") And ((rellaw.projcodeid) =" & xProjCodeid & ")) " _
    & "ORDER BY Val([sectionno]),rellaw.lawno;"
    
    strSection = "SELECT section.sectionno, section.section, section.sectionid, Val([sectionno]) AS vSectionNo, rellaw.projcodeid, rellaw.chapterid " _
    & "FROM [section] INNER JOIN rellaw ON section.sectionid = rellaw.sectionid " _
    & "GROUP BY section.sectionno, section.section, section.sectionid, Val([sectionno]), rellaw.projcodeid, rellaw.chapterid " _
    & "HAVING (((rellaw.projcodeid) = " & xProjCodeID & ") And ((rellaw.chapterid) = " & xChapterID & ")) " _
    & "ORDER BY Val([sectionno]);"


    '=================================================================================================================================
    Set rstSection = DB.OpenRecordset(strSection)
    '=============================================================
    ' With 02
    '=============================================================
    With rstSection
    .MoveFirst
    .MoveLast
    .MoveFirst
    rnSection = rstSection.RecordCount
    Debug.Print "rnSection: " & rnSection
    If rnSection > 0 Then
        Debug.Print "rnSection: " & rnSection
    End If
    '=============================================================
    ' Loop 02 Section
    '=============================================================
    For iSection = 1 To rnSection
        If frmProjCode!mNote = True Then
            
            'text = text & "\P" & Chr(9) & RsPart!MPART & "\P"
            Debug.Print rstSection!section
            CodeText = CodeText
        Else
            'codetext = codetext & "\P" & "Section " & rstSection!sectionno & Chr(9) & rstSection!section & "\P"
            'Set MTextObj = ThisDrawing.ModelSpace.AddMText(corner, width, text)
            CodeText = "Section " & rstSection!sectionno & Chr(9) & rstSection!section & "\P"
        End If
        '=================================================================================================================================
        '######### Write Section
        '=================================================================================================================================
        Set mtextObj = ThisDrawing.ModelSpace.AddMText(TextPosition, width, CodeText)
        mtextObj.Update
        mtextObj.GetBoundingBox minText, maxText
        'TextPosition(1) = minText(1) + TextPosition(1)
        TextPosition(1) = minText(1)
        strTextPosition = "Section X: " & TextPosition(0) & "Y: " & TextPosition(1) + 8
        Set mPositionObj = ThisDrawing.ModelSpace.AddMText(TextPosition, width, strTextPosition)
        mPositionObj.Update
        '=================================================================================================================================
        '######### Write Section End
        '=================================================================================================================================
        '<<<<<<<<<<<<<<<<<<<<<<<<<<<<<<<<<<<<<<<<<<<<<<<<<<<<<<<<<<<<<<<<<<<<<<<<<<<<<<<<<<<<<<<<<<<
        xSectionId = rstSection!sectionid
        
        '=================================================================================================================================
        '=================================================================================================================================
        ' Related CodePara
        '=================================================================================================================================
        '=================================================================================================================================
        CodeText = ""
        strCodePara = " SELECT rellaw.lawno, rellaw.relLawId, rellaw.tblName, rellaw.codeid, rellaw.chapterid, rellaw.sectionid, rellaw.subsectionid, " _
        & "rellaw.paraid, rellaw.rellawmemo, rellaw.input, rellaw.projcodeid, rellaw.sectionid " _
        & "FROM rellaw " _
        & "WHERE (((rellaw.projcodeid) = " & xProjCodeID & ") And ((rellaw.sectionid) = " & xSectionId & ")) " _
        & "ORDER BY rellaw.lawno;"
        mTab = 12
        TextPosition(0) = mTab + TextPosition(0)
        Set rstCodePara = DB.OpenRecordset(strCodePara)
        '=============================================================
        ' Loop 03 Para
        '=============================================================
        Do While Not rstCodePara.EOF
        
        'codetext = codetext & "\P" & rstCodePara!lawno & Chr(9) & rstCodePara!tblname & Chr(9) & rstCodePara!paraid & "\P"
        Select Case rstCodePara!tblName
        '+++++++++++++++++++++++++++++++++++++++++++++
        Case "subsection"
        
            strCodeText = "SELECT Val([subsectionno]) AS Expr1, subsection.lawno, rellaw.projcodeid, rellaw.tblname, rellaw.paraid, subsection.sectionid, subsection.subsection, subsection.subsectionid " _
            & "FROM subsection INNER JOIN rellaw ON subsection.subsectionid = rellaw.subsectionid " _
            & "GROUP BY Val([subsectionno]), subsection.lawno, rellaw.projcodeid, rellaw.tblname, rellaw.paraid, subsection.sectionid, subsection.subsection, subsection.subsectionid " _
            & "HAVING (((rellaw.projcodeid) = 39) And ((subsection.sectionid) = 269)) " _
            & "ORDER BY Val([subsectionno]), subsection.lawno;"
            Set rstCodeText = DB.OpenRecordset(strCodeText)
            tmpCodeText = rstCodeText!subsection
            tmpException = writeException(xProjCodeID, rstCodeText!tblName, rstCodeText!paraid)
            tmpMemo = ""
            If IsNull(rstCodePara!rellawmemo) = False Then
           

            tmpMemo = rstCodePara!rellawmemo
            End If
            
            rstCodeText.Close
            Set rstCodeText = Nothing
        '+++++++++++++++++++++++++++++++++++++++++++++
        Case "codepara1"
            'codetext = codetext & "\P" & "xxxPara1" & "\P"
            strCodeText = "SELECT codepara1.codepara1id, codepara1.codepara1no, codepara1.lawno, codepara1.codepara1 " _
            & "FROM codepara1 " _
            & "WHERE (((codepara1.codepara1id) =" & rstCodePara!paraid & ")) " _
            & "ORDER BY codepara1.lawno;"
            Set rstCodeText = DB.OpenRecordset(strCodeText)
            'Do While Not rstCodeText.EOF
            tmpCodeText = rstCodeText!codepara1
            tmpMemo = ""
            If IsNull(rstCodePara!rellawmemo) = False Then
            tmpMemo = rstCodePara!rellawmemo
            End If
            
            rstCodeText.Close
            Set rstCodeText = Nothing
            'Loop
        Case "codepara2"
            'codetext = codetext & "\P" & "xxxPara2" & "\P"
            strCodeText = "SELECT codepara2.codepara2id, codepara2.codepara2no, codepara2.lawno, codepara2.codepara2 " _
            & "FROM codepara2 " _
            & "WHERE (((codepara2.codepara2id) =" & rstCodePara!paraid & ")) " _
            & "ORDER BY codepara2.lawno;"
            Set rstCodeText = DB.OpenRecordset(strCodeText)
            'Do While Not rstCodeText.EOF
            tmpCodeText = rstCodeText!codepara2
            tmpMemo = ""
    
            If IsNull(rstCodePara!rellawmemo) = False Then
            tmpMemo = rstCodePara!rellawmemo
            End If
            rstCodeText.Close
            Set rstCodeText = Nothing
        
        Case "codepara3"
            'codetext = codetext & "\P" & "xxxPara3" & "\P"
            strCodeText = "SELECT codepara3.codepara3id, codepara3.codepara3no, codepara3.lawno, codepara3.codepara3 " _
            & "FROM codepara3 " _
            & "WHERE (((codepara3.codepara3id) =" & rstCodePara!paraid & ")) " _
            & "ORDER BY codepara3.lawno;"
            Set rstCodeText = DB.OpenRecordset(strCodeText)
            'Do While Not rstCodeText.EOF
            tmpCodeText = rstCodeText!codepara3
            tmpMemo = ""
            If IsNull(rstCodePara!rellawmemo) = False Then
            tmpMemo = rstCodePara!rellawmemo
            End If
            rstCodeText.Close
            Set rstCodeText = Nothing
        
        Case "codeepara4"
            'codetext = codetext & "\P" & "xxxPara4" & "\P"
            strCodeText = "SELECT codepara4.codepara4id, codepara4.codepara4no, codepara4.lawno, codepara4.codepara4 " _
            & "FROM codepara4 " _
            & "WHERE (((codepara4.codepara4id) =" & rstCodePara!paraid & ")) " _
            & "ORDER BY codepara4.lawno;"
            Set rstCodeText = DB.OpenRecordset(strCodeText)
            'Do While Not rstCodeText.EOF
            tmpCodeText = rstCodeText!codepara4
            tmpMemo = ""
            If IsNull(rstCodePara!rellawmemo) = False Then
            tmpMemo = rstCodePara!rellawmemo
            End If
            rstCodeText.Close
            Set rstCodeText = Nothing
        Case "exception"
            'codetext = codetext & "\P" & "xxxPara4" & "\P"
             strCodeText = "SELECT exception.exceptionid, exception.exceptionno, exception.exception, exception.codepara1id, exception.codepara2id, exception.lawno, exception.subsectionid, exception.sectionid, exception.tblname, exception.paraid, exception.codeid " _
            & "FROM [exception] " _
            & "WHERE (((exception.exceptionid) =" & rstCodePara!paraid & ")) " _

            
            Set rstCodeText = DB.OpenRecordset(strCodeText)
            'Do While Not rstCodeText.EOF
            tmpCodeText = rstCodeText!exception
            tmpMemo = ""
            If IsNull(rstCodePara!rellawmemo) = False Then
            tmpMemo = rstCodePara!rellawmemo
            End If
            rstCodeText.Close
            Set rstCodeText = Nothing
            'exception
        End Select
        
nextiPara:
    If (tmpMemo) = "" Then
        CodeText = CodeText & "\P" & rstCodePara!lawno & Chr(9) & tmpCodeText & "\P"
    Else
        'codetext = codetext & "\P" & rstCodePara!lawno & Chr(9) & tmpCodeText & "\P" & "\P" & BigText(tmpMemo) & "\P"
        CodeText = CodeText & "\P" & rstCodePara!lawno & Chr(9) & tmpCodeText & "\P"
        TblPT(0) = mTab + TextPosition(0)
        TblEndPT(0) = TblPT(0) + 32
        ThisDrawing.ModelSpace.AddLine TblPT, TblEndPT
        CodeText = CodeText & "\P" & BigText(tmpMemo) & "\P"
        
    End If
    tmpMemo = ""
        rstCodePara.MoveNext
        Loop
        '=============================================================
        ' Loop 03 Para End
        '=============================================================
End03:
               
        rstCodePara.Close
        Set rstCodePara = Nothing
    '-----------------------------------------------------------------------------------------------------
    
    '>>>>>>>>>>>>>>>>>>>>>>>>>>>>>>>>>>>>>>>>>>>>>>>>>>>>>>>>>>>>>>>>>>>>>>>>>>>>>>>>>>>>>>>>>>>>>>
    '>>>>>>>>>>>>>>>>>>>>>>>>>>>>>>>>>>>>>>>>>>>>>>>>>>>>>>>>>>>>>>>>>>>>>>>>>>>>>>>>>>>>>>>>>>>>>>
    '>>>>>>>>>>>>>>>>>>>>>>>>>>>>>>>>>>>>>>>>>>>>>>>>>>>>>>>>>>>>>>>>>>>>>>>>>>>>>>>>>>>>>>>>>>>>>>
    
    '=================================================================================================================================
    '######### Write Para
    '=================================================================================================================================
    'startPoint(0) = 0#: startPoint(1) = 0#: startPoint(2) = 0#
    '1440 x 0.5 = 720
    
    Set mtextObj = ThisDrawing.ModelSpace.AddMText(TextPosition, width, CodeText)
    mtextObj.Update
    mtextObj.GetBoundingBox minText, maxText
    TextPosition(0) = 0#
    'TextPosition(1) = minText(1) + TextPosition(1)
    TextPosition(1) = minText(1)
    strTextPosition = "Section X: " & TextPosition(0) & "Y: " & TextPosition(1)
    Set mPositionObj = ThisDrawing.ModelSpace.AddMText(TextPosition, width, strTextPosition)
    mPositionObj.Update
    CodeText = ""
    '=================================================================================================================================
    '######### Write Para End
    '=================================================================================================================================
'=============================================================
' Loop 02 Section end
'=============================================================
    rstSection.MoveNext
    Next iSection
    End With
    rstSection.Close
'rstChapter.MoveNext
'=============================================================
' Loop 01 end
'=============================================================
Next iChapter
                'rstSubSection.Close
               ' Set rstSubSection = Nothing
                'rstCodePara1.Close
                'Set rstCodePara1 = Nothing
                'rstCodePara2.Close
                'Set rstCodePara2 = Nothing
                'rstCodePara3.Close
                'Set rstCodePara3 = Nothing
                
                
'Set mtextObj = ThisDrawing.ModelSpace.AddMText(startPoint, width, codetext)
'mtextObj.Update
End With
'=============================================================
'With 01 End
'=============================================================
rstChapter.Close

Set rstChapter = Nothing
DB.Close
'mtextObj.GetBoundingBox minExt, maxExt
'SizestartPoint(0) = 0#: SizestartPoint(1) = minExt(1) + 0#: SizestartPoint(2) = 0#
'textobjSize = "minExt: " & minExt(1) & " maxExt: " & maxExt(1)
'Set mtextobjsize = ThisDrawing.ModelSpace.AddMText(SizestartPoint, width, textobjSize)
'mtextobjsize.Update

Debug.Print rnPart & rnAt & rnPara1
       
End Function
'**********************************************************************************************************
'**********************************************************************************************************
'**********************************************************************************************************
'**********************************************************************************************************
'**********************************************************************************************************
'**********************************************************************************************************
'**********************************************************************************************************
'**********************************************************************************************************
'**********************************************************************************************************
'**********************************************************************************************************

Function writeException(xProjCodeID, strTblName, xVarID As Variant)
Dim DB As Database
Dim rstRelException As Recordset
Dim strException As String
Dim rnChapter, rnSection, rnSubSection, rnCodePara1 As Integer
writeException = ""
Set DB = OpenDatabase("\\jwja-svr-10\jdb\DB_CODE\2018-Code-01.mdb")
strException = "SELECT rellaw.lawno, rellaw.relLawId, rellaw.tblName, rellaw.codeid, rellaw.chapterid, rellaw.sectionid, " _
& "rellaw.subsectionid, rellaw.rellawmemo, rellaw.paraid, rellaw.input, rellaw.projcodeid, rellaw.codepara2id, exception.tblname, " _
& "exception.exception, exception.subsectionid, exception.sectionid " _
& "FROM rellaw INNER JOIN [exception] ON rellaw.paraid = exception.exceptionid " _
& "WHERE (((rellaw.tblName)='exception') AND ((rellaw.projcodeid)=" & xProjCodeID & ") AND ((exception.tblname)='" & strTblName & "') AND ((exception.subsectionid)=" & xVarID & ")) " _
& "ORDER BY rellaw.lawno;"


Set rstRelException = DB.OpenRecordset(strException)
With rstRelException
rnRelException = rstRelException.RecordCount
If IsNull(rnRelException) = True Then
Exit Function
Else
For iRelException = 1 To rnRelException
writeException = writeException & "\P" & rstRelException!lawno & Chr(9) & rstRelException!exception & "\P"
Debug.Print writeException
Next iRelException
End If
End With
End Function

Sub CreateCNstyle_spec()
Dim newText As AcadTextStyle
Dim blnFoundText As Boolean
Dim blnFoundTitle As Boolean
Dim blnFoundSub As Boolean
   
'reset blnFound
blnFoundText = False
blnFoundTitle = False
blnFoundSub = False

    For i = 0 To ThisDrawing.TextStyles.Count - 1  'make the styles for the form
        Debug.Print ThisDrawing.TextStyles(i).Name
        If ThisDrawing.TextStyles(i).Name = "CN" Then
            blnFoundText = True
            Exit Sub
        End If
        
    Next i

Set newText = ThisDrawing.TextStyles.Add("CN")

typeface = "Courier new"
newText.SetFont typeface, Bold, Italic, Charset, PitchandFamily

End Sub

Attribute VB_Name = "Mod_Room"
Public Sub writeRoom()
Dim DB As Database
Dim rstRoom As Recordset
Dim strRoom As String
Dim nRm As Integer    'ProjSet no.
Dim iattr_Room As Integer
'Dim rcArray As Variant
Dim TblPT(0 To 2) As Double
Dim tblPT2(0 To 2) As Double
Dim TblEndPT(0 To 2) As Double

Dim txtHt As Double
Dim textObj As AcadText
Dim attributeObj As AcadAttribute
Dim blockRefObj As AcadBlockReference
'Dim BlkObj As Object
'Dim acadPol As AcadLWPolyline 'MOD 9/9/14
'Dim textObj As AcadText 'MOD 9/9/14
Dim txtSecHt As Double
TblPT(0) = 0: TblPT(1) = 0: TblPT(2) = 0
tblPT2(0) = -300: tblPT2(1) = 0: tblPT2(2) = 0
txtHt = 4
txtRow = ""
mode = acAttributeModeVerify

'2'-8" X 1'-4"
nRmNoDWG = "\\jwja-svr-10\drawfile\jvba\X_rmno01.dwg"
nJumpHead = 0
nJumpRmNoROW = 16 '1'-4" X 12
nJumpUnit = 24 '1'-4" X 12
nJumpFl = 48
nJumpSector = 48
Set DB = OpenDatabase("\\jwja-svr-10\jdb\db_misc\door02_01.mdb")
'xProj_no = frmCode.seleproj
xProj_no = frmDoor.seleproj
strSector = "SELECT SECTOR.SECTORID, SECTOR.SECTORORDER, SECTOR.SECTOR, SECTOR.SECTORNOTE, SECTOR.PROJ_NO " _
& "FROM SECTOR " _
& "WHERE (((SECTOR.PROJ_NO)='" & xProj_no & "'))" _
& "order by sector;"
Set rstSector = DB.OpenRecordset(strSector)
rstSector.MoveLast
rstSector.MoveFirst
If rstSector.RecordCount = 0 Then
    GoTo Exit_writeroom
End If
With rstSector 'with 0
    Do While Not rstSector.EOF
    mSectorID = !Sectorid
    
    '******************WRITE SECTOR************************
    '*****************************************************
    'Set blockRefObj = ThisDrawing.ModelSpace.InsertBlock _
                        (tblPT, nRmNoDWG, 1, 1, 1, 0)
    Debug.Print sector
    'Debug.Print !sector.sector
    Debug.Print !sector
    If IsNull(!sector) = False Then
    txtHt = 6
    'Set MTextObj = ThisDrawing.ModelSpace.AddMText(corner, WIDTH, text)
    TblPT(0) = TblPT(0) - 48
    TblPT(1) = TblPT(1) + 12
    Set textObj = ThisDrawing.ModelSpace.AddText _
                ("Sector: " & !sector, TblPT, txtHt)
    TblPT(1) = TblPT(1) - 6
    TblEndPT(0) = TblPT(0) + 96: TblEndPT(1) = TblPT(1): TblEndPT(2) = TblPT(2)
    'Set acadPol = ThisDrawing.ModelSpace.AddLightWeightPolyline(tblPT, tblEndPT)
    ThisDrawing.ModelSpace.AddLine TblPT, TblEndPT
    TblPT(0) = TblPT(0) + 48
    TblPT(1) = TblPT(1) - 6
    End If
    '*****************************************************
        strFl = "SELECT Floor.flID, Floor.floor, Floor.proj_no, Floor.floornote, floor.sectorid " _
        & "FROM floor where floor.sectorid =" & mSectorID & " " _
        & "order by floor;"
        Set rstFl = DB.OpenRecordset(strFl)
        'rstFl.MoveLast
        'rstFl.MoveFirst
        ReccountFl = rstFl.RecordCount
    '******************Jump Sector************************
    '*****************************************************
        If rstFl.RecordCount = 0 Then
            GoTo GotoNextSector
        End If
            With rstFl 'With 1
                rstFl.MoveLast
                rstFl.MoveFirst
                countFl = 0
                Do While Not rstFl.EOF
                ReccountFl = rstFl.RecordCount
                'countFl = countFl + 1
                Debug.Print "Floor: " & countFl & "-" & !floor
                
                mFlID = !flid
                    strUnit = "SELECT Unit.flid, Unit.unitid, Unit.unitorder, Unit.unitno, Unit.unitname, Unit.unitnote " _
                                & "FROM Unit " _
                                & "WHERE (((Unit.flid) =" & mFlID & ")) " _
                                & "ORDER BY Unit.unitorder;"
                    Set rstUnit = DB.OpenRecordset(strUnit)
                    RecCountUnit = rstUnit.RecordCount
        '******************Jump Floor ************************
        '*****************************************************
                    If rstUnit.RecordCount = 0 Then
                        GoTo GotoNextFloor
                    End If
                    rstUnit.MoveLast
                    rstUnit.MoveFirst
                    With rstUnit 'With 2
                    
                    rstUnit.MoveLast
                    rstUnit.MoveFirst
                    countUnit = 0
                    Do While Not rstUnit.EOF
                    munitID = !unitid
                    countUnit = countUnit + 1
                    Debug.Print "Unit: " & countUnit & "-" & !unitno
                    strRm = "SELECT ROOM.RMID, ROOM.RMORDER, ROOM.RMNO, ROOM.RMNAME, ROOM.PDRID, ROOM.NOTE, ROOM.PROJ_NO, " _
                            & "ROOM.FLID, ROOM.UnitID, ROOM.FRMNO " _
                            & "FROM ROOM " _
                            & "WHERE (((room.unitid) =" & munitID & ")) " _
                            & "ORDER BY ROOM.RMORDER;"
                            Set rstRoom = DB.OpenRecordset(strRm)
                            'rstRoom.MoveLast
                            'rstRoom.MoveFirst
        '******************Jump Unit  ************************
        '*****************************************************
                            If rstRoom.RecordCount = 0 Then
                                GoTo GotoNextUnit
                            End If
                            RecCountRm = rstRoom.RecordCount
                            nRmNo = rstRoom.RecordCount
                            With rstRoom 'With 3
                                'For i3 = 0 To nRmNo - 1
                                countRm = 0
                               Do While Not rstRoom.EOF
                                    countRm = countRm + 1
                                    Debug.Print "Room: " & countRm & "-" & !rmno
                                    Set blockRefObj = ThisDrawing.ModelSpace.InsertBlock _
                                                                 (TblPT, nRmNoDWG, 1, 1, 1, 0)
                                    Dim varAttributes1 As Variant
                                    varAttributes1 = blockRefObj.GetAttributes
                                    For iattr_RMrow = LBound(varAttributes1) To UBound(varAttributes1)
                                        '************ Xrmno ***************************************************************
                                        If varAttributes1(iattr_RMrow).TagString = "XRMNO" Then
                                            If IsNull(!FRMNO) = True Then '++++++++++++++++++++++++++++++++++++++++++
                                                varAttributes1(iattr_RMrow).textString = ""
                                            Else
                                                varAttributes1(iattr_RMrow).textString = !FRMNO
                                                
                                            End If
                                        End If
                                        '************ Xrmname ***************************************************************
                                        If varAttributes1(iattr_RMrow).TagString = "XRMNAME" Then
                                            If IsNull(!FRMNO) = True Then '++++++++++++++++++++++++++++++++++++++++++
                                                varAttributes1(iattr_RMrow).textString = ""
                                            Else
                                                If IsNull(!RMNAME) = True Then
                                                varAttributes1(iattr_RMrow).textString = "CHECK!"
                                                Else
                                                varAttributes1(iattr_RMrow).textString = !RMNAME
                                                End If
                                                
                                            End If
                                        End If
                                    
                                    Next iattr_RMrow
                                    TblPT(1) = TblPT(1) - nJumpRmNoROW
                                    .MoveNext
                                    'Next i3
                                Loop
                                
                            End With 'With 3
                            rstRoom.Close
GotoNextUnit:
                            .MoveNext
                            TblPT(1) = TblPT(1) - nJumpUnit
                       Loop
                
                             End With 'With 2
                                     'rstunit.Close
GotoNextFloor:
                .MoveNext
                TblPT(1) = TblPT(1) - nJumpFl
                Loop
            
            End With 'With 1
GotoNextSector:
    .MoveNext
    TblPT(1) = TblPT(1) - nJumpSector
    
    Loop
End With 'with 0
'rstfl.Close

Set DB = Nothing

Exit_writeroom:
rstSector.Close
'rstRoom.Close
rstUnit.Close
rstFl.Close

'frmCode.HIDE
frmDoor.Hide

Set DB = Nothing
End Sub

Attribute VB_Name = "Mod_Sched"
Option Explicit
Public Sub SCHEDULES2()
   frmSched_CSI.show 'MOD 9/9/14
End Sub
Public Sub SCHEDULES()
   frmDoor.show
End Sub

Sub test()
Dim x As String
x = SEPTEXT2("UN CERAMIC MOSAIC tile", 2, 2, 12)
Debug.Print "x: " & x
End Sub

Sub mkDr()


Dim DB As Database
Dim RsDRG As Recordset
Dim strDRG As String
Dim rnDRG As Integer
Dim rcArray As Variant
Dim TblPT(0 To 2) As Double
Dim tblWidth As Double
Dim txtHt As Double
Dim textObj As AcadText
Dim attributeObj As AcadAttribute
Dim height As Double
Dim mode As Long
Dim prompt, txtRow As String
Dim tag As String
Dim value As String
Dim blockRefObj As AcadBlockReference
Dim attData() As AcadObject
Dim nBubdwg As Variant
Dim EntGrp(0), i, ati As Integer
Dim EntPrp(0) As Variant
Dim BlkObj As Object
Dim Pt1(0) As Double
Dim Pt2(0) As Double
'ThisDrawing.SelectionSets.Item("TBLK").Delete
'create a selection set
'Set SSNew = ThisDrawing.SelectionSets.Add("TBLK")
'Filter for Group code 2, the block name
'EntGrp(0) = 2
'The name of the block to filter for
'EntPrp(0) = "xdrschedrow01"
'find the block
'SSNew.Select acSelectionSetAll, Pt1, Pt2, EntGrp, EntPrp
'If a block is found
'If SSNew.Count >= 1 Then






frmDoor.ListBox1.Clear
CreateCNstyle


Set DB = OpenDatabase("\\jwja-svr-10\jdb\db_misc\Door02_01.mdb")

strDRG = "SELECT DRGP.DRGID, DRGP.DRID, DRGP.PROJ_NO, DRGP.DRGNO, DRGP.DRTYPE, " _
& "DRGP.DRFIN, DRGP.DRFRAME, DRGP.DRJAMB, DRGP.DRHEAD, DRGP.HDSET, DRGP.DRGNOTE, " _
& "DR.DRWIDTH, DR.DRHEIGHT, DR.DRMAT, DR.DRTHK, DR.DRMFGR, DR.DRFIRE, DR.DRNOTE, DR.OLDSIZE " _
& "FROM DRGP INNER JOIN DR ON DRGP.DRID = DR.DRID " _
& "WHERE (((DRGP.PROJ_NO) = '" & frmDoor.seleproj & "')) " _
& "ORDER BY DRGP.DRGNO;"

'drgno drtype,
'nBubdwg = "H:\drawfile\jvba\XBUBdre_01.dwg"  'MOD 5/18/15

'**************************************************************
'nBubdwg = "H:\drawfile\jvba\XBUBdrAR.dwg"  'MOD 6/5/15
'InsertJBlock "e:\drawfile\jvba\xdrschedrow02.dwg", tblPT, "Model"
'**************************************************************
'**************************************************************
nBubdwg = "\\jwja-svr-10\drawfile\jvba\XBUBdrAR.dwg"  'MOD 6/5/15
InsertJBlock "\\jwja-svr-10\drawfile\jvba\xdrschedrow02.dwg", TblPT, "Model"
'**************************************************************




Set RsDRG = DB.OpenRecordset(strDRG)
If RsDRG.RecordCount = 0 Then
GoTo ExitMKDR
End If
rnDRG = RsDRG.RecordCount
Debug.Print rnDRG
TblPT(0) = 0: TblPT(1) = 0: TblPT(1) = 0
txtHt = 4
txtRow = ""
mode = acAttributeModeVerify
'***********************************************************************************************
'ThisDrawing.ModelSpace.InsertBlock tblPT, "e:\drawfile\jvba\xdrschedhead01.dwg", 1, 1, 1, 0
'ThisDrawing.ModelSpace.InsertBlock tblPT, "H:\drawfile\jvba\xdrschedhead02.dwg", 1, 1, 1, 0
ThisDrawing.ModelSpace.InsertBlock TblPT, "\\jwja-svr-10\drawfile\jvba\xdrschedhead02.dwg", 1, 1, 1, 0
'***********************************************************************************************
TblPT(1) = TblPT(1) - 144

RsDRG.MoveFirst
With RsDRG
    For i = 1 To rnDRG
         Set blockRefObj = ThisDrawing.ModelSpace.InsertBlock _
                     (TblPT, "xdrschedrow02", 1, 1, 1, 0)

        'Set blockRefObj = ThisDrawing.ModelSpace.InsertBlock _
               (insertionPnt, "xdrschedrow01", 1#, 1#, 1#, 0)
        'set blcokrefobj = thisdrawing.modelspace.Name.ObjectName "xdrschedrow01"
         
        '******************************
          'Get the block's attributes
                Dim varAttributes As Variant
                varAttributes = blockRefObj.GetAttributes
               
                    For ati = LBound(varAttributes) To UBound(varAttributes)
                    Debug.Print varAttributes(ati).TagString
                        If varAttributes(ati).TagString = "XDrno" Then
                            If IsNull(!DRGNO) = True Then
                                varAttributes(ati).textString = ""
                            Else
                                varAttributes(ati).textString = !DRGNO
                                '***************************************************************
                                '*      INSERT BUBBLE
                                '***************************************************************
                                                TblPT(0) = TblPT(0) - 48
                                                Set blockRefObj = ThisDrawing.ModelSpace.InsertBlock _
                                                             (TblPT, nBubdwg, 1, 1, 1, 0)
                                                Dim varAttributesB As Variant
                                                varAttributesB = blockRefObj.GetAttributes
                                                varAttributesB(0).textString = ![DRGNO]
                                                
                                                TblPT(0) = TblPT(0) + 48
                                
                                '***************************************************************
                            End If

                        End If
                        If varAttributes(ati).TagString = "xdrsize" Then
                            If IsNull(!OLDSIZE) = True Then
                                varAttributes(ati).textString = ""
                            Else
                                varAttributes(ati).textString = !OLDSIZE
                            End If

                        End If
                        If varAttributes(ati).TagString = "XDRTYPE" Then
                            If IsNull(!DRTYPE) = True Then
                                varAttributes(ati).textString = ""
                            Else
                                varAttributes(ati).textString = !DRTYPE
                            End If

                        End If
                        If varAttributes(ati).TagString = "XDRTHK" Then
                            If IsNull(!DRTHK) = True Then
                                varAttributes(ati).textString = ""
                            Else
                                varAttributes(ati).textString = !DRTHK
                            End If

                        End If
                        If varAttributes(ati).TagString = "XDRCON" Then
                            If IsNull(!DRMAT) = True Then
                                varAttributes(ati).textString = ""
                            Else
                                varAttributes(ati).textString = !DRMAT
                            End If
                        End If
                        If varAttributes(ati).TagString = "XDRFAC" Then
                            If IsNull(!DRFIN) = True Then
                                varAttributes(ati).textString = ""
                            Else
                                varAttributes(ati).textString = !DRFIN
                            End If
                        End If
        '***************************************************
                        If varAttributes(ati).TagString = "XFRTYPE" Then
                            If IsNull(!DRFRAME) = True Then
                                varAttributes(ati).textString = ""
                            Else
                                varAttributes(ati).textString = !DRFRAME
                            End If
                        End If
        '***************************************************
                        If varAttributes(ati).TagString = "XDRJ" Then
                            If IsNull(!drjamb) = True Then
                                varAttributes(ati).textString = ""
                            Else
                                varAttributes(ati).textString = !drjamb
                            End If
                        End If
                        If varAttributes(ati).TagString = "XDRH" Then
                            If IsNull(!DRHEAD) = True Then
                                varAttributes(ati).textString = ""
                            Else
                                varAttributes(ati).textString = !DRHEAD
                            End If
                        End If
                        If varAttributes(ati).TagString = "XDRF" Then
                            If IsNull(!DRFIRE) = True Then
                                varAttributes(ati).textString = ""
                            Else
                                varAttributes(ati).textString = !DRFIRE
                            End If
                        End If
                        If varAttributes(ati).TagString = "XDRHD" Then
                            If IsNull(!HDSET) = True Then
                                varAttributes(ati).textString = ""
                            Else
                                varAttributes(ati).textString = !HDSET
                            End If
                        End If
                        If varAttributes(ati).TagString = "XDRREM" Then
                            If IsNull(!DRGNOTE) = True Then
                                varAttributes(ati).textString = ""
                            Else
                                varAttributes(ati).textString = !DRGNOTE
                            End If
                        End If

                    Next ati
                'attributeObj.Update
        
                '************************************************
                'txtRow = !drgno & Chr(9) & !oldsize
                'Set textObj = ThisDrawing.ModelSpace.AddText(txtRow, tblPT, txtHT)
                '******************************************************
                'textObj.StyleName = "cn"
                'textObj.Update
                TblPT(1) = TblPT(1) - 12
        .MoveNext
        
    Next i
End With
'ThisDrawing.SelectionSets.Item("TBLK").Delete
RsDRG.Close
Set DB = Nothing
'Else
'ThisDrawing.SelectionSets.Item("TBLK").Delete
'no attribute block, inform the user

'MsgBox "Inserted block! Re-run this program.", vbCritical, "JWJA"

'delete the selection set
'ThisDrawing.SelectionSets.Item("TBLK").Delete
'End If

'Set MTextObj = ThisDrawing.ModelSpace.AddMText(corner, width, text)

'ThisDrawing.SelectionSets.Item("TBLK").Delete


ExitMKDR:
frmDoor.Hide
End Sub
Public Sub MkHDWR()


Dim DB As Database
Dim RstHDProjSet, RsHDwrSet As Recordset
Dim strHDSet, strHDProjSet, txtRow As String
Dim rnHDPS As Integer   'ProjSet no.
Dim rnHDS As Integer    'EachSet No.
'Dim rcArray As Variant
Dim TblPT(0 To 2) As Double
Dim tblPT2(0 To 2) As Double
Dim tblWidth As Double
Dim txtHt As Double
Dim textObj As AcadText
Dim attributeObj As AcadAttribute
Dim height As Double
Dim mode As Long
Dim prompt As String
'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

Dim xHDWRSETID, i, iatHG, rnHDWR, k, iatHW As Integer
'*************************************************************************
'*************************************************************************
Dim nHeadDwg, nGroupDwg, nRowDwg, nFootDwg As Variant
Dim nJumpHead, nJumpGroup, nJumpRow As Integer

'*************************************************************************
'*************************************************************************


    'If Not IsNull(ThisDrawing.SelectionSets.Item("hdwrsched")) Then
        'Set SSNew = ThisDrawing.SelectionSets.Item("hdwrsched")
        'SSNew.Delete
    'End If

'create a selection set
'ThisDrawing.SelectionSets.Item("hdwrsched").Delete

''Set SSNew = ThisDrawing.SelectionSets.Add("hdwrsched")
'Filter Type: for Group code 2, the block name
''FilterGp(0) = 2
'Filter Data: The name of the block to filter for
''FilterDt(0) = "XHDWRROW01"
'find the block
'SSNew.Select acSelectionSetAll, Pt1, Pt2, FilterGp, FilterDt
'If a block is found
''If SSNew.Count >= 1 Then

'If SSNew.Count >= 0 Then




frmDoor.ListBox1.Clear
CreateCNstyle


Set DB = OpenDatabase("\\jwja-svr-10\jdb\db_misc\Door02_01.mdb")

strHDProjSet = "SELECT HDWRSET.HDWRSETID, HDWRSET.PROJ_NO, HDWRSET.HDWRSETNOTE, HDWRSET.HDWRSETNO " _
& "FROM HDWRSET " _
& "WHERE (((HDWRSET.PROJ_NO)='" & frmDoor.seleproj & "'));"

'strHDSet = "SELECT HDWRSET.HDWRSETID, HDWRCONN.SETQTY, HDWR.TYPE, HDWR.CAT, HDWR.MFGR, HDWR.FIN, HDWR.HDWRNOTE, HDWR.HDIMGNAME, HDWR.HDWRDESC " _
& "FROM HDWRSET INNER JOIN (HDWR INNER JOIN HDWRCONN ON HDWR.HDID = HDWRCONN.HDID) ON HDWRSET.HDWRSETID = HDWRCONN.HDWRSETID " _
& "WHERE (((HDWRSET.HDWRSETID)=" & xHDWRSETID & "));"

strHDSet = "SELECT HDWRCONN.HDWRSETID, " _
                        & "HDWRCONN.SETQTY, HDWR.TYPE, HDWR.CAT, HDWR.MFGR, HDWR.FIN, HDWR.HDWRNOTE, HDWR.HDIMGNAME, HDWR.HDWRDESC " _
                        & "FROM HDWR INNER JOIN HDWRCONN ON HDWR.HDID = HDWRCONN.HDID " _
                        & "WHERE (((HDWRCONN.HDWRSETID)=" & xHDWRSETID & "));"

'& "WHERE (((HDWRSET.HDWRSETID)=576));"
'" _
'& "WHERE (((HDWRSET.HDWRSETID)=" & xHDWRSETID & "))"
'& "WHERE (((HDWRSET.HDWRSETID)=578));"


RecordSets:
Set RstHDProjSet = DB.OpenRecordset(strHDProjSet, dbOpenDynaset)

If RstHDProjSet.RecordCount = 0 Then
    GoTo ExitMKHDWR
End If


TblPT(0) = 0: TblPT(1) = 0: TblPT(2) = 0
tblPT2(0) = -300: tblPT2(1) = 0: tblPT2(2) = 0
txtHt = 4
txtRow = ""
mode = acAttributeModeVerify
'InsertJBlock "e:\drawfile\jvba\XHDWRHEAD01.dwg", tblPT, "Model"

'++++++++++++++++++++++++++++++++++++++++++++++++++++++++++++++++++++++++++++++
'++++++++++++++++++++++++++++++++++++++++++++++++++++++++++++++++++++++++++++++

    nHeadDwg = "\\jwja-svr-10\drawfile\jvba\XHDWRHEAD02.dwg"
    nGroupDwg = "\\jwja-svr-10\drawfile\jvba\XHDWRGPROW02.dwg"
    nRowDwg = "\\jwja-svr-10\drawfile\jvba\XHDWRROW02.dwg"
    nFootDwg = "\\jwja-svr-10\drawfile\jvba\XHDWRFOOT02.dwg"
    nJumpHead = 24
    nJumpGroup = 36
    nJumpRow = 12
    InsertJBlock "\\jwja-svr-10\drawfile\jvba\XHDWRHEAD03.dwg", TblPT, "Model"

'++++++++++++++++++++++++++++++++++++++++++++++++++++++++++++++++++++++++++++++
'++++++++++++++++++++++++++++++++++++++++++++++++++++++++++++++++++++++++++++++


ThisDrawing.ModelSpace.InsertBlock TblPT, "\\jwja-svr-10\drawfile\jvba\XHDWRHEAD02.dwg", 1, 1, 1, 0
InsertJBlock "\\jwja-svr-10\drawfile\jvba\XHDWRGPROW02.dwg", tblPT2, "Model"
InsertJBlock "\\jwja-svr-10\drawfile\jvba\XHDWRROW02.dwg", tblPT2, "Model"
InsertJBlock "\\jwja-svr-10\drawfile\jvba\XHDWRFOOT02.dwg", tblPT2, "Model"

'ThisDrawing.SelectionSets.Item("XHDWRGPROW01").Delete
'ThisDrawing.SelectionSets.Item("XHDWRROW01").Delete

TblPT(1) = TblPT(1) - 24
RstHDProjSet.MoveLast
RstHDProjSet.MoveFirst
rnHDPS = RstHDProjSet.RecordCount
Debug.Print rnHDPS

With RstHDProjSet
    For i = 1 To rnHDPS
         xHDWRSETID = !HDWRSETID
         Set blockRefObj = ThisDrawing.ModelSpace.InsertBlock _
                     (TblPT, "XHDWRGPROW02", 1, 1, 1, 0)

        'Set blockRefObj = ThisDrawing.ModelSpace.InsertBlock _
               (insertionPnt, "xdrschedrow01", 1#, 1#, 1#, 0)
        'set blcokrefobj = thisdrawing.modelspace.Name.ObjectName "xdrschedrow01"
         
        '******************************
          'Get the block's attributes
                Dim varAttributes As Variant
                varAttributes = blockRefObj.GetAttributes
               
                    For iatHG = LBound(varAttributes) To UBound(varAttributes)
                    
                    Debug.Print varAttributes(iatHG).TagString
                        If varAttributes(iatHG).TagString = "XHDSETNO" Then
                            If IsNull(!HDWRSETNO) = True Then
                                varAttributes(iatHG).textString = ""
                            Else
                                varAttributes(iatHG).textString = !HDWRSETNO
                                Debug.Print varAttributes(iatHG).textString
                            End If

                        End If
                        If varAttributes(iatHG).TagString = "XHDSETNOTE" Then
                            If IsNull(!HDWRSETNOTE) = True Then
                                varAttributes(iatHG).textString = ""
                            Else
                                varAttributes(iatHG).textString = !HDWRSETNOTE
                            End If

                        End If
                    Next iatHG
                        TblPT(1) = TblPT(1) - 36
                        xHDWRSETID = !HDWRSETID
                        Debug.Print xHDWRSETID
                        'RstHDSet.Close
                        Set RsHDwrSet = DB.OpenRecordset("SELECT HDWRCONN.HDWRSETID, " _
                        & "HDWRCONN.SETQTY, HDWR.TYPE, HDWR.CAT, HDWR.MFGR, HDWR.FIN, HDWR.HDIMGNAME, HDWR.HDWRDESC " _
                        & "FROM HDWR RIGHT JOIN HDWRCONN ON HDWR.HDID = HDWRCONN.HDID " _
                        & "WHERE (((HDWRCONN.HDWRSETID)=" & xHDWRSETID & "));")
 '& xHDWRSETID & "));", dbOpenDynaset)
                        Debug.Print RsHDwrSet.RecordCount
                        'Debug.Print strHDSet

                        
                        If RsHDwrSet.RecordCount = 0 Then
                            GoTo ExitMKHDWR
                        End If
                        RsHDwrSet.MoveLast
                        RsHDwrSet.MoveFirst
                        Debug.Print RsHDwrSet.RecordCount
                        Debug.Print rnHDWR
                        rnHDWR = RsHDwrSet.RecordCount
                        With RsHDwrSet
                        Debug.Print xHDWRSETID
                            For k = 1 To rnHDWR
                                 Set blockRefObj = ThisDrawing.ModelSpace.InsertBlock _
                                             (TblPT, "XHDWRROW02", 1, 1, 1, 0)

                                Dim varAttributes2 As Variant
                                varAttributes2 = blockRefObj.GetAttributes
                                For iatHW = LBound(varAttributes2) To UBound(varAttributes2)
                                Debug.Print varAttributes2(iatHW).TagString
                                    If varAttributes2(iatHW).TagString = "XQTY" Then
                                        If IsNull(!SETQTY) = True Then
                                            varAttributes2(iatHW).textString = ""
                                        Else
                                            varAttributes2(iatHW).textString = !SETQTY
                                        End If
                                    End If
                                    If varAttributes2(iatHW).TagString = "XTYPE" Then
                                        If IsNull(!Type) = True Then
                                            varAttributes2(iatHW).textString = ""
                                        Else
                                            varAttributes2(iatHW).textString = !Type
                                        End If
                                    End If
                                    If varAttributes2(iatHW).TagString = "XCAT" Then
                                        If IsNull(!cat) = True Then
                                            varAttributes2(iatHW).textString = ""
                                        Else
                                            varAttributes2(iatHW).textString = !cat
                                        End If
                                    End If
                                    If varAttributes2(iatHW).TagString = "XFIN" Then
                                        If IsNull(!FIN) = True Then
                                            varAttributes2(iatHW).textString = ""
                                        Else
                                            varAttributes2(iatHW).textString = !FIN
                                        End If
                                    End If
                                    If varAttributes2(iatHW).TagString = "XMFGR" Then
                                        If IsNull(!MFGR) = True Then
                                            varAttributes2(iatHW).textString = ""
                                        Else
                                            varAttributes2(iatHW).textString = !MFGR
                                        End If
                                    End If
                                    If varAttributes2(iatHW).TagString = "XNOTE" Then
                                        If IsNull(!HDWRDESC) = True Then
                                            varAttributes2(iatHW).textString = ""
                                        Else
                                            varAttributes2(iatHW).textString = Left(!HDWRDESC, 22)
                                        End If
                                    End If
                                Next iatHW
                            
                            TblPT(1) = TblPT(1) - 12
                            .MoveNext
                            Next k
                            End With 'hdwr rows
                   RsHDwrSet.Close
                'attributeObj.Update
        
                '************************************************
                'txtRow = !drgno & Chr(9) & !oldsize
                'Set textObj = ThisDrawing.ModelSpace.AddText(txtRow, tblPT, txtHT)
                '******************************************************
                'textObj.StyleName = "cn"
                'textObj.Update
                Debug.Print "iathw :" & iatHW
        TblPT(1) = TblPT(1)
        .MoveNext
        
    Next i
End With
Set blockRefObj = ThisDrawing.ModelSpace.InsertBlock _
                                             (TblPT, "XHDWRFOOT02", 1, 1, 1, 0)
''ThisDrawing.SelectionSets.Item("hdwrsched").Delete
RstHDProjSet.Close
'RsHDwrSet.Close
Set DB = Nothing

''Else

''ThisDrawing.SelectionSets.Item("hdwrsched").Delete
'no attribute block, inform the user
'

'MsgBox "Inserted block! Re-run this program.", vbCritical, "JWJA"

'delete the selection set
'ThisDrawing.SelectionSets.Item("TBLK").Delete

''End If

'Set MTextObj = ThisDrawing.ModelSpace.AddMText(corner, width, text)

''ThisDrawing.SelectionSets.Item("hdwrsched").Delete


ExitMKHDWR:
frmDoor.Hide

End Sub

'############################################################################
'############################################################################
'#
'#
'#          MkHDWRimg
'#
'#
'#
'############################################################################
'############################################################################

 Public Sub MkHDWRimg()


Dim DB As Database
Dim RstHDProjSet, RsHDwrSet As Recordset
Dim strHDSet, strHDProjSet, txtRow As String
Dim rnHDPS As Integer   'ProjSet no.
Dim rnHDS As Integer    'EachSet No.
'Dim rcArray As Variant
Dim TblPT(0 To 2) As Double
Dim tblPT2(0 To 2) As Double
Dim tblWidth As Double
Dim txtHt As Double
Dim textObj As AcadText
Dim attributeObj As AcadAttribute
Dim height As Double
Dim mode As Long
Dim prompt As String

'**********IMG********************
Dim nHeadDwg, nGroupDwg, nRowDwg, nFootDwg As Variant
Dim nJumpHead, nJumpGroup, nJumpRow As Integer
'**********IMG********************

'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

Dim xHDWRSETID, i, iatHG, rnHDWR, k, iatHW As Integer

    'If Not IsNull(ThisDrawing.SelectionSets.Item("hdwrsched")) Then
        'Set SSNew = ThisDrawing.SelectionSets.Item("hdwrsched")
        'SSNew.Delete
    'End If

'create a selection set
'ThisDrawing.SelectionSets.Item("hdwrsched").Delete

''Set SSNew = ThisDrawing.SelectionSets.Add("hdwrsched")
'Filter Type: for Group code 2, the block name
''FilterGp(0) = 2
'Filter Data: The name of the block to filter for
''FilterDt(0) = "XHDWRROW01"
'find the block
'SSNew.Select acSelectionSetAll, Pt1, Pt2, FilterGp, FilterDt
'If a block is found
''If SSNew.Count >= 1 Then

'If SSNew.Count >= 0 Then




frmDoor.ListBox1.Clear
CreateCNstyle


Set DB = OpenDatabase("\\jwja-svr-10\jdb\db_misc\Door02_01.mdb")

strHDProjSet = "SELECT HDWRSET.HDWRSETID, HDWRSET.PROJ_NO, HDWRSET.HDWRSETNOTE, HDWRSET.HDWRSETNO " _
& "FROM HDWRSET " _
& "WHERE (((HDWRSET.PROJ_NO)='" & frmDoor.seleproj & "'))" _
& "ORDER BY HDWRSET.HDWRSETNO ;"

'strHDSet = "SELECT HDWRSET.HDWRSETID, HDWRCONN.SETQTY, HDWR.TYPE, HDWR.CAT, HDWR.MFGR, HDWR.FIN, HDWR.HDWRNOTE, HDWR.HDIMGNAME, HDWR.HDWRDESC " _
& "FROM HDWRSET INNER JOIN (HDWR INNER JOIN HDWRCONN ON HDWR.HDID = HDWRCONN.HDID) ON HDWRSET.HDWRSETID = HDWRCONN.HDWRSETID " _
& "WHERE (((HDWRSET.HDWRSETID)=" & xHDWRSETID & "));"

strHDSet = "SELECT HDWRCONN.HDWRSETID, " _
                        & "HDWRCONN.SETQTY, HDWR.TYPE, HDWR.CAT, HDWR.MFGR, HDWR.FIN, HDWR.HDWRNOTE, HDWR.HDIMGNAME, HDWR.HDWRDESC " _
                        & "FROM HDWR INNER JOIN HDWRCONN ON HDWR.HDID = HDWRCONN.HDID " _
                        & "WHERE (((HDWRCONN.HDWRSETID)=" & xHDWRSETID & "));"

'& "WHERE (((HDWRSET.HDWRSETID)=576));"
'" _
'& "WHERE (((HDWRSET.HDWRSETID)=" & xHDWRSETID & "))"
'& "WHERE (((HDWRSET.HDWRSETID)=578));"


RecordSets:
Set RstHDProjSet = DB.OpenRecordset(strHDProjSet, dbOpenDynaset)

If RstHDProjSet.RecordCount = 0 Then
    GoTo ExitMKHDWRimg
End If


TblPT(0) = 0: TblPT(1) = 0: TblPT(2) = 0
tblPT2(0) = -300: tblPT2(1) = 0: tblPT2(2) = 0
txtHt = 4
txtRow = ""
mode = acAttributeModeVerify

''InsertJBlock "e:\drawfile\jvba\XHDWRHEAD01.dwg", tblPT, "Model"
'ThisDrawing.ModelSpace.InsertBlock tblPT, "e:\drawfile\jvba\XHDWRHEAD02.dwg", 1, 1, 1, 0
'InsertJBlock "e:\drawfile\jvba\XHDWRGPROW02.dwg", tblPT2, "Model"
'InsertJBlock "e:\drawfile\jvba\XHDWRROW02.dwg", tblPT2, "Model"
'InsertJBlock "e:\drawfile\jvba\XHDWRFOOT02.dwg", tblPT2, "Model"

'ThisDrawing.SelectionSets.Item("XHDWRGPROW01").Delete
'ThisDrawing.SelectionSets.Item("XHDWRROW01").Delete

If frmDoor.Showhdwrimg = True Then
    nHeadDwg = "\\jwja-svr-10\drawfile\jvba\XHDWRHEAD03.dwg"
    nGroupDwg = "\\jwja-svr-10\drawfile\jvba\XHDWRGPROW03.dwg"
    nRowDwg = "\\jwja-svr-10\drawfile\jvba\XHDWRROW03.dwg"
    nFootDwg = "\\jwja-svr-10\drawfile\jvba\XHDWRFOOT03.dwg"
    nJumpHead = 60 'was 24
    nJumpGroup = 24 'was 66
    nJumpRow = 60
    InsertJBlock "\\jwja-svr-10\drawfile\jvba\XHDWRHEAD03.dwg", TblPT, "Model"
Else
    nHeadDwg = "\\jwja-svr-10\drawfile\jvba\XHDWRHEAD02.dwg"
    nGroupDwg = "\\jwja-svr-10\drawfile\jvba\XHDWRGPROW02.dwg"
    nRowDwg = "\\jwja-svr-10\drawfile\jvba\XHDWRROW02.dwg"
    nFootDwg = "\\jwja-svr-10\drawfile\jvba\XHDWRFOOT02.dwg"
    nJumpHead = 24
    nJumpGroup = 36
    nJumpRow = 12
    InsertJBlock "\\jwja-svr-10\drawfile\jvba\XHDWRHEAD02.dwg", TblPT, "Model"
End If

TblPT(1) = TblPT(1) - nJumpHead
RstHDProjSet.MoveLast
RstHDProjSet.MoveFirst
rnHDPS = RstHDProjSet.RecordCount
Debug.Print rnHDPS

With RstHDProjSet
    For i = 1 To rnHDPS
         xHDWRSETID = !HDWRSETID
         Set blockRefObj = ThisDrawing.ModelSpace.InsertBlock _
                     (TblPT, nGroupDwg, 1, 1, 1, 0)

        'Set blockRefObj = ThisDrawing.ModelSpace.InsertBlock _
               (insertionPnt, "xdrschedrow01", 1#, 1#, 1#, 0)
        'set blcokrefobj = thisdrawing.modelspace.Name.ObjectName "xdrschedrow01"
         
        '******************************
          'Get the block's attributes
                Dim varAttributes As Variant
                varAttributes = blockRefObj.GetAttributes
               
                    For iatHG = LBound(varAttributes) To UBound(varAttributes)
                    
                    Debug.Print varAttributes(iatHG).TagString
                        If varAttributes(iatHG).TagString = "XHDSETNO" Then
                            If IsNull(!HDWRSETNO) = True Then
                                varAttributes(iatHG).textString = ""
                            Else
                                varAttributes(iatHG).textString = !HDWRSETNO
                                Debug.Print varAttributes(iatHG).textString
                            End If

                        End If
                        If varAttributes(iatHG).TagString = "XHDSETNOTE" Then
                            If IsNull(!HDWRSETNOTE) = True Then
                                varAttributes(iatHG).textString = ""
                            Else
                                varAttributes(iatHG).textString = !HDWRSETNOTE
                            End If

                        End If
                    Next iatHG
                        TblPT(1) = TblPT(1) - nJumpGroup
                        xHDWRSETID = !HDWRSETID
                        Debug.Print xHDWRSETID
                        'RstHDSet.Close
                        Set RsHDwrSet = DB.OpenRecordset("SELECT HDWRCONN.HDWRSETID, " _
                        & "HDWRCONN.SETQTY, HDWR.TYPE, HDWR.CAT, HDWR.MFGR, HDWR.FIN, HDWR.HDIMGNAME, hdwr.hdwrnote, HDWR.HDWRDESC " _
                        & "FROM HDWR RIGHT JOIN HDWRCONN ON HDWR.HDID = HDWRCONN.HDID " _
                        & "WHERE (((HDWRCONN.HDWRSETID)=" & xHDWRSETID & "));")
 '& xHDWRSETID & "));", dbOpenDynaset)
                        Debug.Print RsHDwrSet.RecordCount
                        'Debug.Print strHDSet

                        
                        If RsHDwrSet.RecordCount = 0 Then
                            GoTo ExitMKHDWRimg
                        End If
                        RsHDwrSet.MoveLast
                        RsHDwrSet.MoveFirst
                        Debug.Print RsHDwrSet.RecordCount
                        Debug.Print rnHDWR
                        rnHDWR = RsHDwrSet.RecordCount
                        With RsHDwrSet
                        Debug.Print xHDWRSETID
                            For k = 1 To rnHDWR
                                 Set blockRefObj = ThisDrawing.ModelSpace.InsertBlock _
                                             (TblPT, nRowDwg, 1, 1, 1, 0)

                                Dim varAttributes2 As Variant
                                varAttributes2 = blockRefObj.GetAttributes
                        '***************************************************************
                                If !hdimgname <> "" Then
                                If frmDoor.Showhdwrimg = True Then
                                    Dim imgPT(0 To 2) As Double
                                    Dim scalefactor, xSF As Double
                                    Dim rotAngleInDegree As Double, rotAngle As Double
                                    'Dim imageName As String
                                    Dim imageName As String
                                
                                    Dim raster As AcadRasterImage
                                    Dim imgheight As Variant
                                    Dim imgwidth As Variant
                                
                                    'imageName = "C:\AutoCAD\sample\downtown.jpg"
                                    imageName = !hdimgname
                                    Debug.Print imageName
                                    'insertionPoint(0) = 2#: insertionPoint(1) = 2#: insertionPoint(2) = 0#
                                    'imgPT(0) = tblPT(0) + 36: imgPT(1) = tblPT(1) - 54: imgPT(2) = tblPT(2)
                                    imgPT(0) = TblPT(0) + 6: imgPT(1) = TblPT(1) - 54: imgPT(2) = TblPT(2)
                                    scalefactor = 48#
                                    'rotAngleInDegree = 0#
                                    'rotAngle = rotAngleInDegree * 3.141592 / 180#
                                    rotAngle = 0#
                                    
                                    
                                    
                                    ' Creates a raster image in model space
                                    'If !fximgname <> "" Then
                                        Set raster = ThisDrawing.ModelSpace.AddRaster(imageName, imgPT, scalefactor, rotAngle)
                                        With raster
                                        imgheight = raster.ImageHeight
                                        imgwidth = raster.ImageWidth
                                            If imgheight > 48 Then
                                                xSF = (48 / imgheight) * 48
                                                Debug.Print "xSF: " & xSF * 48
                                                 raster.scalefactor = xSF
                                            End If
                                        End With
                                    End If
                                End If
                        '***************************************************************

                                
                                
                                
                                For iatHW = LBound(varAttributes2) To UBound(varAttributes2)
                                Debug.Print varAttributes2(iatHW).TagString
                                    If varAttributes2(iatHW).TagString = "XQTY" Then
                                        If IsNull(!SETQTY) = True Then
                                            varAttributes2(iatHW).textString = ""
                                        Else
                                            varAttributes2(iatHW).textString = !SETQTY
                                        End If
                                    End If
                                    If varAttributes2(iatHW).TagString = "XTYPE" Then
                                        If IsNull(!Type) = True Then
                                            varAttributes2(iatHW).textString = ""
                                        Else
                                            varAttributes2(iatHW).textString = !Type
                                        End If
                                    End If
                                    If varAttributes2(iatHW).TagString = "XCAT" Then
                                        If IsNull(!cat) = True Then
                                            varAttributes2(iatHW).textString = ""
                                        Else
                                            varAttributes2(iatHW).textString = !cat
                                        End If
                                    End If
                                    If varAttributes2(iatHW).TagString = "XFIN" Then
                                        If IsNull(!FIN) = True Then
                                            varAttributes2(iatHW).textString = ""
                                        Else
                                            varAttributes2(iatHW).textString = !FIN
                                        End If
                                    End If
                                    If varAttributes2(iatHW).TagString = "XMFGR" Then
                                        If IsNull(!MFGR) = True Then
                                            varAttributes2(iatHW).textString = ""
                                        Else
                                            varAttributes2(iatHW).textString = !MFGR
                                        End If
                                    End If
                                    If varAttributes2(iatHW).TagString = "XNOTE1" Then
                                        If IsNull(!hdwrnote) = True Then
                                        GoTo SkipforNull
                                        End If
                                        If IsNull(SEPTEXT2(!hdwrnote, 1, 2, 48)) = True Or !hdwrnote = "" Then
                                            varAttributes2(iatHW).textString = ""
                                        Else
                                            'varAttributes2(iatHW).TextString = Left(!HDWRDESC, 22)
                                            varAttributes2(iatHW).textString = SEPTEXT2(!hdwrnote, 1, 2, 48)
                                        End If
                                    End If
                                    If varAttributes2(iatHW).TagString = "XNOTE2" Then
                                        If IsNull(!hdwrnote) = True Then
                                        GoTo SkipforNull
                                        End If
                                        If IsNull(SEPTEXT2(!hdwrnote, 2, 2, 48)) = True Or !hdwrnote = "" Then
                                            varAttributes2(iatHW).textString = ""
                                        Else
                                            'varAttributes2(iatHW).TextString = Left(!HDWRDESC, 22)
                                            varAttributes2(iatHW).textString = SEPTEXT2(!hdwrnote, 2, 2, 48)
                                        End If
                                    End If
                                    If varAttributes2(iatHW).TagString = "XDESC1" Then
                                    Debug.Print "*******>>>>> : " & varAttributes2(iatHW).TagString
                                    Debug.Print "*******>>>>> : " & !HDWRDESC
                                    
                                        If IsNull(!HDWRDESC) = True Then
                                        GoTo SkipforNull
                                        End If
                                        If IsNull(SEPTEXT2(!HDWRDESC, 1, 2, 48)) = True Then
                                            varAttributes2(iatHW).textString = ""
                                        Else
                                            'varAttributes2(iatHW).TextString = Left(!HDWRDESC, 22)
                                            varAttributes2(iatHW).textString = SEPTEXT2(!HDWRDESC, 1, 2, 48)
                                            'varAttributes2(iatHW).TextString = Left(!HDWRDESC, 32)
                                        End If
                                    End If
                                    If varAttributes2(iatHW).TagString = "XDESC2" Then
                                        If IsNull(!HDWRDESC) = True Then
                                        GoTo SkipforNull
                                        End If
                                        If IsNull(SEPTEXT2(!HDWRDESC, 2, 2, 48)) = True Then
                                            varAttributes2(iatHW).textString = ""
                                        Else
                                            'varAttributes2(iatHW).TextString = Left(!HDWRDESC, 22)
                                            varAttributes2(iatHW).textString = SEPTEXT2(!HDWRDESC, 2, 2, 48)
                                            'varAttributes2(iatHW).TextString = Left(!HDWRDESC, 32)
                                        End If
                                    End If
                                
                                
                                '**************************
SkipforNull:
                                Next iatHW
                            
                            TblPT(1) = TblPT(1) - nJumpRow
                            .MoveNext
                            Next k
                            End With 'hdwr rows
                   RsHDwrSet.Close
                'attributeObj.Update
        
                '************************************************
                'txtRow = !drgno & Chr(9) & !oldsize
                'Set textObj = ThisDrawing.ModelSpace.AddText(txtRow, tblPT, txtHT)
                '******************************************************
                'textObj.StyleName = "cn"
                'textObj.Update
                Debug.Print "iathw :" & iatHW
        TblPT(1) = TblPT(1)
        .MoveNext
        
    Next i
End With
Set blockRefObj = ThisDrawing.ModelSpace.InsertBlock _
                                             (TblPT, nFootDwg, 1, 1, 1, 0)
''ThisDrawing.SelectionSets.Item("hdwrsched").Delete
RstHDProjSet.Close

'RsHDwrSet.Close
Set DB = Nothing

''Else

''ThisDrawing.SelectionSets.Item("hdwrsched").Delete
'no attribute block, inform the user
'

'MsgBox "Inserted block! Re-run this program.", vbCritical, "JWJA"

'delete the selection set
'ThisDrawing.SelectionSets.Item("TBLK").Delete

''End If

'Set MTextObj = ThisDrawing.ModelSpace.AddMText(corner, width, text)

''ThisDrawing.SelectionSets.Item("hdwrsched").Delete


ExitMKHDWRimg:
frmDoor.Hide

End Sub


Public Sub Start()
  'InsertADrawing "Z:\Blocks\C_Paper.dwg", "Model"
End Sub
'############################################################################
'############################################################################
'#
'#
'#      writeWinImg     2014-09-08
'#
'#
'#
'############################################################################
'############################################################################
Public Sub writeWinImg()
Dim DB As Database
Dim RstProjWin, RstProjWinItem As Recordset
Dim strProjWin, strProjWinItem, txtRow As String
Dim rnProjWin As Integer   'ProjSet no.
Dim rnProjWinItem As Integer    'EachSet No.
'Dim rcArray As Variant
Dim TblPT(0 To 2) As Double
Dim tblPT2(0 To 2) As Double
Dim tblWidth As Double
Dim txtHt As Double
Dim textObj As AcadText
Dim attributeObj As AcadAttribute
Dim height As Double
Dim mode As Long
Dim prompt As String

'**********IMG********************
Dim nHeadDwg, nGroupDwg, nRowDwg, nFootDwg, nBubdwg As Variant
Dim nJumpHead, nJumpGroup, nJumpRow, rn As Integer
'**********IMG********************

'Dim tag As String
'Dim value As String
Dim blockRefObj As AcadBlockReference

'Dim attData() As AcadObject

'Dim FilterGp(0) As Integer
'Dim FilterDt(0) As Variant
Dim BlkObj As Object
'Dim Pt1(0) As Double
'Dim Pt2(0) As Double

Dim xProjWinID, i, iatProjWin, k, iatProjWinItem As Integer
frmDoor.ListBox1.Clear
CreateCNstyle
'############################################################################
'#         Set DB
'############################################################################

Set DB = OpenDatabase("\\jwja-svr-10\jdb\db_misc\Door02_01.mdb")

'############################################################################
'#         Set Points
'############################################################################

TblPT(0) = 0: TblPT(1) = 0: TblPT(2) = 0
tblPT2(0) = -300: tblPT2(1) = 0: tblPT2(2) = 0
txtHt = 4
txtRow = ""
mode = acAttributeModeVerify
'############################################################################
'#         Set DWG List
'############################################################################
If frmDoor.writeWindImg = True Then
    nHeadDwg = "\\jwja-svr-10\drawfile\jvba\XWINSCHED_HD02.dwg"
    'nGroupDwg = "Z:\jvba\XHDWRGPROW03.dwg"
    nRowDwg = "\\jwja-svr-10\drawfile\jvba\XWINSCHED_ROW02.dwg"
    'nFootDwg = "H:\drawfile\jvba\XHDWRFOOT03.dwg"
    nBubdwg = "\\jwja-svr-10\drawfile\jvba\XWINSCHED_BUB01.dwg"
    nJumpHead = 72 'was 24
    'nJumpGroup = 24 'was 66
    nJumpRow = 72
    'InsertJBlock "H:\drawfile\jvba\XHDWRHEAD03.dwg", tblPT, "Model"
ElseIf frmDoor.writeWindShort = True Then
    nHeadDwg = "\\jwja-svr-10\drawfile\jvba\XWINSCHED_HD01.dwg"
    'nGroupDwg = "H:\drawfile\jvba\XHDWRGPROW02.dwg"
    nRowDwg = "\\jwja-svr-10\drawfile\jvba\XWINSCHED_ROW01.dwg"
    'nFootDwg = "H:\drawfile\jvba\XHDWRFOOT02.dwg"
    nBubdwg = "\\jwja-svr-10\drawfile\jvba\XWINSCHED_BUB01.dwg"
    nJumpHead = 48
    'nJumpGroup = 36
    nJumpRow = 16
    'InsertJBlock "H:\drawfile\jvba\XHDWRHEAD02.dwg", tblPT, "Model"
ElseIf frmDoor.writeWindLong = True Then
    nHeadDwg = "\\jwja-svr-10\drawfile\jvba\XWINDSCHED_HD03.dwg"
    'nGroupDwg = "H:\drawfile\jvba\XHDWRGPROW02.dwg"
    nRowDwg = "\\jwja-svr-10\drawfile\jvba\XWINDSCHED_ROW03.dwg" 'XWINDSCHED_ROW03
    'nFootDwg = "H:\drawfile\jvba\XHDWRFOOT02.dwg"
    nBubdwg = "\\jwja-svr-10\drawfile\jvba\XWINSCHED_BUB01.dwg"
    nJumpHead = 60 '5x12
    'nJumpGroup = 36
    nJumpRow = 24 '2x12
    'InsertJBlock "H:\drawfile\jvba\XHDWRHEAD02.dwg", tblPT, "Model"

End If
'############################################################################
'#         rstProjWin
'############################################################################
    strProjWin = "SELECT projwin.projwinid, projwin.proj_no, projwin.connprojwin, projwin.PROJWINDNAME, projwin.note, projwin.input " _
    & "FROM projwin " _
    & "WHERE (((projwin.proj_no) = '" & frmDoor.seleproj & "')) " _
    & "ORDER BY projwin.projwinid;"
RecordSets:
    Set RstProjWin = DB.OpenRecordset(strProjWin, dbOpenDynaset)

If RstProjWin.RecordCount = 0 Then
    GoTo ExitWindImg
End If
'RstHDProjSet.MoveLast
'RstHDProjSet.MoveFirst
rnProjWin = RstProjWin.RecordCount
Debug.Print rnProjWin
'############################################################################
'#         Write Head
'############################################################################

With RstProjWin   'WITH 1
     xProjWinID = !projwinid
     Set blockRefObj = ThisDrawing.ModelSpace.InsertBlock _
                 (TblPT, nHeadDwg, 1, 1, 1, 0)
    'Set blockRefObj = ThisDrawing.ModelSpace.InsertBlock _
           (insertionPnt, "xdrschedrow01", 1#, 1#, 1#, 0)
    'set blcokrefobj = thisdrawing.modelspace.Name.ObjectName "xdrschedrow01"
    '******************************
    'Get the block's attributes
    Dim varAttributes0 As Variant
    varAttributes0 = blockRefObj.GetAttributes
    
    For iatProjWin = LBound(varAttributes0) To UBound(varAttributes0)
    '############################################################################
    '#         XPROJ_NO
    '############################################################################
    Debug.Print varAttributes0(iatProjWin).TagString
    If varAttributes0(iatProjWin).TagString = "XPROJ_NO" Then
        If IsNull(!PROJ_NO) = True Then
            varAttributes0(iatProjWin).textString = ""
        Else
            varAttributes0(iatProjWin).textString = !PROJ_NO
            Debug.Print varAttributes0(iatProjWin).textString
        End If
    End If
    '############################################################################
    '#         XDATE
    '############################################################################
    Debug.Print varAttributes0(iatProjWin).TagString
    If varAttributes0(iatProjWin).TagString = "XDATE" Then
        'If IsNull(!Proj_no) = True Then
            'varAttributes0(iatProjWin).TextString = ""
        'Else
            varAttributes0(iatProjWin).textString = Date
            Debug.Print varAttributes0(iatProjWin).textString
        'End If
    End If
    '############################################################################
    '#         XPROJ_WINDSCHEDNAME
    '############################################################################
    Debug.Print varAttributes0(iatProjWin).TagString
    If varAttributes0(iatProjWin).TagString = "XPROJ_WINDSCHEDNAME" Then
        If IsNull(!PROJWINDNAME) = True Then
            varAttributes0(iatProjWin).textString = ""
        Else
            varAttributes0(iatProjWin).textString = !PROJWINDNAME
            Debug.Print varAttributes0(iatProjWin).textString
        End If
    End If
    
    Next iatProjWin
    TblPT(1) = TblPT(1) - nJumpHead

    '############################################################################
    '#         Write Rows
    '############################################################################
    strProjWinItem = "SELECT projwin.projwinid, connprojwin.connprojwinid, connprojwin.projwinno, connprojwin.projwinnoTE, " _
    & "WINDOW.WINSIZE, WINDOW.CATNO, WINDOW.WINMAT, WINDOW.WINTYPE, WINDOW.WINMODEL, WINDOW.WINAREA, window.winmfgr, " _
    & "WINDOW.WINFIN, WINDOW.WINGL, WINDOW.WINNOTE, WINDOW.WINOPENAREA, WINDOW.WINIMGNAME, WINDOW.WINGL, WINDOW.UFACTOR, WINDOW.SHGC, WINDOW.VT, WINDOW.AIRLEAK, " _
    & "Contact.COMPANY " _
    & "FROM ((projwin INNER JOIN connprojwin ON projwin.projwinid = connprojwin.projwinid) " _
    & "INNER JOIN WINDOW ON connprojwin.winid = WINDOW.WINID) " _
    & "INNER JOIN Contact ON WINDOW.WINMFGR = Contact.CID " _
    & "WHERE (((projwin.projwinid)=" & xProjWinID & ")) " _
    & "ORDER BY connprojwin.PROJWINNO;"
    
    '& "FROM (projwin INNER JOIN connprojwin ON projwin.projwinid = connprojwin.projwinid) " _
    '& "INNER JOIN WINDOW ON connprojwin.winid = WINDOW.WINID " _

    
    Set RstProjWinItem = DB.OpenRecordset(strProjWinItem)
    rnProjWinItem = RstProjWinItem.RecordCount
    Debug.Print rnProjWinItem
    RstProjWinItem.MoveLast
    RstProjWinItem.MoveFirst
    With RstProjWinItem 'With 2
        
        'Do Until RstProjWinItem.EOF = True
        For k = 1 To rnProjWinItem
            Set blockRefObj = ThisDrawing.ModelSpace.InsertBlock _
                        (TblPT, nRowDwg, 1, 1, 1, 0)
        Dim varAttributes As Variant
        varAttributes = blockRefObj.GetAttributes
                        
                        
            Debug.Print "Win No.: " & !projwinno
            '############################################################################
            '#         Image
            '############################################################################
            If !WINIMGNAME <> "" Then
                'If frmDoor.showWinImg = True Then
                '############################################################################
                '#         EDITED 18/10/28
                '############################################################################
                If frmDoor.writeWindImg = True Then
                    Dim imgPT(0 To 2) As Double
                    Dim scalefactor, xSF As Double
                    Dim rotAngleInDegree As Double, rotAngle As Double
                    'Dim imageName As String
                    Dim imageName As String
                
                    Dim raster As AcadRasterImage
                    Dim imgheight As Variant
                    Dim imgwidth As Variant
                
                    'imageName = "C:\AutoCAD\sample\downtown.jpg"
                    imageName = !WINIMGNAME
                    Debug.Print imageName
                    'insertionPoint(0) = 2#: insertionPoint(1) = 2#: insertionPoint(2) = 0#
                    'imgPT(0) = tblPT(0) + 36: imgPT(1) = tblPT(1) - 54: imgPT(2) = tblPT(2)
                    'imgPT(0) = tblPT(0) + 6: imgPT(1) = tblPT(1) - 54: imgPT(2) = tblPT(2)
                    imgPT(0) = TblPT(0) + 42: imgPT(1) = TblPT(1) - 60: imgPT(2) = TblPT(2)
                    'scalefactor = 48#
                    scalefactor = 60#
                    'rotAngleInDegree = 0#
                    'rotAngle = rotAngleInDegree * 3.141592 / 180#
                    rotAngle = 0#
                    
                    
                    
                    ' Creates a raster image in model space
                    'If !fximgname <> "" Then
                    Set raster = ThisDrawing.ModelSpace.AddRaster(imageName, imgPT, scalefactor, rotAngle)
                    With raster
                    imgheight = raster.ImageHeight
                    imgwidth = raster.ImageWidth
                        If imgheight > 60 Then
                            xSF = (60 / imgheight) * 60
                            Debug.Print "xSF: " & xSF * 60
                             raster.scalefactor = xSF
                        End If
                    End With
                End If
            End If
            '***************************************************************

            
            
            For iatProjWinItem = LBound(varAttributes) To UBound(varAttributes)
            Debug.Print varAttributes(iatProjWinItem).TagString
                '############################################################################
                '#         XWINNO
                '############################################################################
                If varAttributes(iatProjWinItem).TagString = "XWINNO" Then
                    If IsNull(!projwinno) = True Then
                        varAttributes(iatProjWinItem).textString = ""
                    Else
                        varAttributes(iatProjWinItem).textString = !projwinno
                    '############################################################################
                    '#         WINBUBBLE
                    '############################################################################
                        
                        Dim varAttributes2 As Variant
                        Dim iatBub As Integer
                        TblPT(0) = TblPT(0) - 48
                        Set blockRefObj = ThisDrawing.ModelSpace.InsertBlock _
                                        (TblPT, nBubdwg, 1, 1, 1, 0)
                        varAttributes2 = blockRefObj.GetAttributes
                        For iatBub = LBound(varAttributes2) To UBound(varAttributes2)
                        Debug.Print iatBub
                            If varAttributes2(iatBub).TagString = "WINNO" Then
                                If IsNull(!projwinno) = True Then
                                    varAttributes2(iatBub).textString = ""
                                Else
                                    varAttributes2(iatBub).textString = !projwinno
                                End If
                            End If
                        Next iatBub
                        TblPT(0) = TblPT(0) + 48
                    '############################################################################
                    End If
                End If
                '############################################################################
                '#         XWINSIZE
                '############################################################################
                If varAttributes(iatProjWinItem).TagString = "XWINSIZE" Then
                    If IsNull(!WINSIZE) = True Then
                        varAttributes(iatProjWinItem).textString = ""
                    Else
                        varAttributes(iatProjWinItem).textString = !WINSIZE
                    End If
                End If
                '############################################################################
                '#         XWINTYPE1
                '############################################################################
                If varAttributes(iatProjWinItem).TagString = "XWINTYPE1" Then
                    If IsNull(!WINTYPE) = True Then
                        varAttributes(iatProjWinItem).textString = ""
                    Else
                        varAttributes(iatProjWinItem).textString = SEPTEXT2(!WINTYPE, 1, 2, 12)
                    End If
                End If
                '############################################################################
                '#         XWINTYPE2
                '############################################################################
                If varAttributes(iatProjWinItem).TagString = "XWINTYPE2" Then
                    If IsNull(!WINTYPE) = True Then
                        varAttributes(iatProjWinItem).textString = ""
                    Else
                        varAttributes(iatProjWinItem).textString = SEPTEXT2(!WINTYPE, 2, 2, 12)
                    End If
                End If
                
                '############################################################################
                '#         XWINCAT
                '############################################################################
                If varAttributes(iatProjWinItem).TagString = "XWINCAT" Then
                    If IsNull(!CATNO) = True Then
                        varAttributes(iatProjWinItem).textString = ""
                    Else
                        varAttributes(iatProjWinItem).textString = !CATNO
                    End If
                End If
                '############################################################################
                '#         XWINMAT
                '############################################################################
                If varAttributes(iatProjWinItem).TagString = "XWINMAT" Then
                    If IsNull(!WINMAT) = True Then
                        varAttributes(iatProjWinItem).textString = ""
                    Else
                        varAttributes(iatProjWinItem).textString = !WINMAT
                    End If
                End If
                '############################################################################
                '#         XWINMODEL
                '############################################################################
                If varAttributes(iatProjWinItem).TagString = "XWINMODEL" Then
                    If IsNull(!WINMODEL) = True Then
                        varAttributes(iatProjWinItem).textString = ""
                    Else
                        varAttributes(iatProjWinItem).textString = !WINMODEL
                    End If
                End If
                '############################################################################
                '#         XWINFIN
                '############################################################################
                If varAttributes(iatProjWinItem).TagString = "XWINFIN" Then
                    If IsNull(!WINFIN) = True Then
                        varAttributes(iatProjWinItem).textString = ""
                    Else
                        varAttributes(iatProjWinItem).textString = !WINFIN
                    End If
                End If
                '############################################################################
                '#         XWINGL
                '############################################################################
                If varAttributes(iatProjWinItem).TagString = "XWINGL" Then
                    If IsNull(!WINGL) = True Then
                        varAttributes(iatProjWinItem).textString = ""
                    Else
                        varAttributes(iatProjWinItem).textString = !WINGL
                    End If
                End If
                '############################################################################
                '#         XWINNO
                '############################################################################
                If varAttributes(iatProjWinItem).TagString = "XWINNO" Then
                    If IsNull(!projwinno) = True Then
                        varAttributes(iatProjWinItem).textString = ""
                    Else
                        varAttributes(iatProjWinItem).textString = !projwinno
                    End If
                End If
                '############################################################################
                '#         XWINMFGR
                '############################################################################
                
                
                If varAttributes(iatProjWinItem).TagString = "XWINMFGR" Then
                    If IsNull(!COMPANY) = True Then
                        varAttributes(iatProjWinItem).textString = ""
                    Else
                        
                        varAttributes(iatProjWinItem).textString = !COMPANY
                        'varAttributes(iatProjWinItem).TextString = DLookUp("company", "contact", "[cid]= 1122")
                    End If
                End If
                '############################################################################
                '#         XWINNOTE
                '############################################################################
                If varAttributes(iatProjWinItem).TagString = "XWINNOTE" Then
                    If IsNull(!WINNOTE) = True Then
                        varAttributes(iatProjWinItem).textString = ""
                    Else
                        varAttributes(iatProjWinItem).textString = !WINNOTE
                    End If
                End If
                '############################################################################
                '#         XWINREMARK1
                '############################################################################
                If varAttributes(iatProjWinItem).TagString = "XWINREMARK1" Then
                    If IsNull(!projwinnote) = True Then
                        varAttributes(iatProjWinItem).textString = ""
                    Else
                        varAttributes(iatProjWinItem).textString = SEPTEXT2(!projwinnote, 1, 2, 18)
                    End If
                End If
                '############################################################################
                '#         XWINREMARK2
                '############################################################################
                If varAttributes(iatProjWinItem).TagString = "XWINREMARK2" Then
                    If IsNull(!projwinnote) = True Then
                        varAttributes(iatProjWinItem).textString = ""
                    Else
                        varAttributes(iatProjWinItem).textString = SEPTEXT2(!projwinnote, 2, 2, 18)
                    End If
                End If
                
                
                
                '############################################################################
                '#         XWINREMARK
                '############################################################################
                If varAttributes(iatProjWinItem).TagString = "XWINREMARK" Then
                    If IsNull(!projwinnote) = True Then
                        varAttributes(iatProjWinItem).textString = ""
                    Else
                        varAttributes(iatProjWinItem).textString = !projwinnote
                    End If
                End If
                
                
                
                '############################################################################
                '#         XU
                '############################################################################
                If varAttributes(iatProjWinItem).TagString = "XU" Then
                    If IsNull(!UFACTOR) = True Then
                        varAttributes(iatProjWinItem).textString = ""
                    Else
                        varAttributes(iatProjWinItem).textString = !UFACTOR
                    End If
                End If
                '############################################################################
                '#         SHGC
                '############################################################################
                If varAttributes(iatProjWinItem).TagString = "SHGC" Then
                    If IsNull(!SHGC) = True Then
                        varAttributes(iatProjWinItem).textString = ""
                    Else
                        varAttributes(iatProjWinItem).textString = !SHGC
                    End If
                End If
                '############################################################################
                '#         XWVT
                '############################################################################
                If varAttributes(iatProjWinItem).TagString = "XWVT" Then
                    If IsNull(!VT) = True Then
                        varAttributes(iatProjWinItem).textString = ""
                    Else
                        varAttributes(iatProjWinItem).textString = !VT
                    End If
                End If
                '############################################################################
                '#         XWAIR
                '############################################################################
                If varAttributes(iatProjWinItem).TagString = "XWAIR" Then
                    If IsNull(!AIRLEAK) = True Then
                        varAttributes(iatProjWinItem).textString = ""
                    Else
                        varAttributes(iatProjWinItem).textString = !AIRLEAK
                    End If
                End If
            
            
            
            
            
            
            
            Next iatProjWinItem
            TblPT(1) = TblPT(1) - nJumpRow
            .MoveNext
            Debug.Print "K: " & k
        Next k
        'tblPT(1) = tblPT(1) - nJumpRow
        '.MoveNext
    End With 'With 2
    


End With    'WITH 1
ExitWindImg:
RstProjWin.Close
RstProjWinItem.Close

Set DB = Nothing
frmDoor.Hide

End Sub

Attribute VB_Name = "Mod_Spec"

 Public Function Num2Frac(ByVal x As Double) As String
      Dim Fixed As Double, Temp As String
        x = Abs(x)
        Fixed = Int(x)
        If Fixed > 0 Then
          Temp = CStr(Fixed)
        End If
        Select Case x - Fixed
          Case 0.1 To 0.145
            Temp = Temp + " 1/8"
          Case 0.145 To 0.182
            Temp = Temp + " 1/6"
          Case 0.182 To 0.225
            Temp = Temp + " 1/5"
          Case 0.225 To 0.29
            Temp = Temp + " 1/4"
          Case 0.29 To 0.35
            Temp = Temp + " 1/3"
          Case 0.35 To 0.3875
            Temp = Temp + " 3/8"
          Case 0.3875 To 0.45
            Temp = Temp + " 2/5"
          Case 0.45 To 0.55
            Temp = Temp + " 1/2"
          Case 0.55 To 0.6175
            Temp = Temp + " 3/5"
          Case 0.6175 To 0.64
            Temp = Temp + " 5/8"
          Case 0.64 To 0.7
            Temp = Temp + " 2/3"
          Case 0.7 To 0.775
            Temp = Temp + " 3/4"
          Case 0.775 To 0.8375
            Temp = Temp + " 4/5"
          Case 0.8735 To 0.91
            Temp = Temp + " 7/8"
          Case Is > 0.91
            Temp = CStr(Int(x) + 1)
        End Select
        Num2Frac = Temp
      End Function

Public Sub jSpec() '10/13/13
frmSpec.show
End Sub


Function printspec(xProjCSIID As Integer)
Dim DB As Database
Dim RsPart, RsPat, RsPpara1 As Recordset
Dim strPpart, strPat, strPpara1 As String
Dim rnPart, rnAt, rnPara1 As Integer
Dim specArray() As Variant

'**********************************************************************************************************
'**********************************************************************************************************
'H_H_Jspec05_CURRENT
'Set DB = OpenDatabase("H:\db\db_SPEC\H_H_JSPEC04_02.mdb") '10/5/14
'Set DB = OpenDatabase("H:\db\db_SPEC\H_H_Jspec05_CURRENT.mdb") '12/22/17 'X_JSPEC_17_01
Set DB = OpenDatabase("\\jwja-svr-10\jdb\db_SPEC\X_JSPEC_17_01.mdb")
'**********************************************************************************************************
'**********************************************************************************************************

strPCSI = "SELECT PROJCSI.PROJCSIID, PROJCSI.PROJCSIDATE, PROJCSI.PROJSPECID, " _
& "PROJCSI.PROJ_NO, MCSI.MCSIID, MCSI.MCSI, MCSI.MCSINAME " _
& "FROM MCSI INNER JOIN PROJCSI ON MCSI.MCSIID = PROJCSI.MCSIID " _
& "WHERE (((PROJCSI.PROJCSIID)=" & xProjCSIID & "));"
'& "ORDER BY DRGP.DRGNO;"

Set RsCSI = DB.OpenRecordset(strPCSI)
rnCSI = RsCSI.RecordCount



With RsCSI
For iCSI = 1 To rnCSI
    Debug.Print "xprojcsiid : " & xProjCSIID
    UserForm1.TextBox1 = RsCSI!mCSI
    'strPpart = "SELECT PROJPART.PROJPARTID, PROJPART.PROJCSIID, PROJPART.PROJPARTNO, " _
    & "MPART.MPARTID, MPART.MPART FROM MPART INNER JOIN PROJPART ON PROJPART.MPARTID=mpart.MPARTID " _
    & "WHERE (((PROJPART.PROJCSIID)=" & xProjCSIID & "));"
    strPpart = "SELECT PROJPART.PROJPARTID, PROJPART.PROJCSIID, PROJPART.PROJPARTNO, MPART.MPARTID, MPART.MPART " _
    & "FROM MPART INNER JOIN PROJPART ON MPART.MPARTID = PROJPART.MPARTID " _
    & "WHERE (((PROJPART.PROJCSIID)=" & xProjCSIID & "))" _
    & "ORDER BY PROJPART.PROJPARTNO;"
    Set RsPart = DB.OpenRecordset(strPpart, dbOpenDynaset)
        With RsPart
        .MoveFirst
        .MoveLast
        .MoveFirst
        rnPart = RsPart.RecordCount
        Debug.Print "rnPart: " & rnPart
    
        For iPart = 1 To rnPart
            UserForm1.TextBox1 = UserForm1.TextBox1 & vbCrLf & RsPart!MPART
            xProjpartid = !projpartid
            strPat = "SELECT PROJAT.PROJATID, PROJAT.PROJPARTID, PROJAT.PROJATNO, " _
            & "MAT.MATID, MAT.MAT FROM MAT INNER JOIN PROJAT ON MAT.MATID=PROJAT.MATID " _
            & "WHERE (((PROJat.PROJpartid)=" & xProjpartid & "))" _
            & "ORDER BY PROJAT.PROJATNO;"
            Set Rsat = DB.OpenRecordset(strPat, dbOpenDynaset)
                With Rsat
                '.MoveFirst
                '.MoveLast
                '.MoveFirst
                rnAt = Rsat.RecordCount
                Debug.Print "rnat: " & rnAt
            
                For iat = 1 To rnAt
                    UserForm1.TextBox1 = UserForm1.TextBox1 & vbCrLf & Chr(9) & Rsat!Mat
                    xProjatid = !projatid
                    
                    strPpara1 = "SELECT PROJPARA1.PROJPARA1ID, PROJPARA1.PROJATID, PROJPARA1.PROJPARA1NO, " _
                    & "MPARA1.MPARA1ID, MPARA1.MPARA1 FROM PROJPARA1 INNER JOIN MPARA1 ON PROJPARA1.MPARA1ID=MPARA1.MPARA1ID " _
                    & "WHERE (((PROJpara1.PROJatid)=" & xProjatid & "));" _
                    & "ORDER BY PROJPARA1.PROJPARA1NO;"
                
                    Set Rspara1 = DB.OpenRecordset(strPpara1)
                        With Rspara1
                        .MoveLast
                        .MoveFirst
                            rnPara1 = Rspara1.RecordCount
                            For ipara1 = 1 To rnPara1
                                UserForm1.TextBox1 = UserForm1.TextBox1 & vbCrLf & Chr(9) & Chr(9) & Rspara1!Mpara1
                                xProjpara1id = !projpara1id
                                
                        '-------------------------------------------------------------------------
                                
                                Rspara1.MoveNext
                            Next ipara1
                        End With 'rspara1
                    
                    
                    '-------------------------------------------------------------------------
                    
                    Rsat.MoveNext
                    Next iat
                End With 'rsat
            
            
            '-------------------------------------------------------------------------
            RsPart.MoveNext
            Next iPart
        End With 'rspart
Next iCSI

End With 'rscsi



Debug.Print rnPart & rnAt & rnPara1
'Do Until RsPart.EOF = True

'    UserForm1.TextBox1 = RsPart!MPART
   ' RsPart.MoveNext
    
'Loop
End Function
'**********************************************************************************************************


'**********************************************************************************************************
'**********************************************************************************************************
'**********************************************************************************************************
'**********************************************************************************************************
'
'12/22/17
'
'***/*******************************************************************************************************
'**********************************************************************************************************
'**********************************************************************************************************
'**********************************************************************************************************


Function writemtext(xProjCSIID As Integer)
'On Error GoTo Err_writemtext
Dim DB As Database
Dim RsPart, RsPat, RsPpara1 As Recordset
Dim strPpart, strPat, strPpara1, text As String
Dim rnPart, rnAt, rnPara1 As Integer
Dim specArray() As Variant
Dim corner(0 To 2) As Double
Dim width As Double
Dim mATno As Integer


'**********************************************************************************************************
'**********************************************************************************************************
Set DB = OpenDatabase("\\jwja-svr-10\jdb\db_SPEC\X_JSPEC_17_01.mdb")
'**********************************************************************************************************
'**********************************************************************************************************

strPCSI = "SELECT PROJCSI.PROJCSIID, PROJCSI.PROJCSIDATE, PROJCSI.PROJSPECID, " _
& "PROJCSI.PROJ_NO, MCSI.MCSIID, MCSI.MCSI, MCSI.MCSINAME " _
& "FROM MCSI INNER JOIN PROJCSI ON MCSI.MCSIID = PROJCSI.MCSIID " _
& "WHERE (((PROJCSI.PROJCSIID)=" & xProjCSIID & "));"


Set RsCSI = DB.OpenRecordset(strPCSI)
rnCSI = RsCSI.RecordCount

corner(0) = 0#: corner(1) = 0#: corner(2) = 0#
'WIDTH = 384 '32' X 12
'*********************************************************************************************
'*********************************************************************************************
' 12/22/17
'*********************************************************************************************
'*********************************************************************************************
If frmSpec.OptionButton1.value Then
    mSCF = 48
    width = mSCF * 8 '48 x 8 = 384
ElseIf frmSpec.OptionButton2.value Then
    mSCF = 96
    width = mSCF * 8 '96 x 8 = 768
ElseIf frmSpec.OptionButton3.value Then
    mSCF = 64
    width = mSCF * 8 '64 x 8 = 512
End If

xScF8 = mSCF / 12 * 2
xScF6 = mSCF / 12 * 1.5
xScF4 = mSCF / 12 * 1
'*********************************************************************************************
'*********************************************************************************************

text = ""
mATno = 1

With RsCSI
For iCSI = 1 To rnCSI
    Debug.Print "xprojcsiid : " & xProjCSIID
'*********************** Format Start CSIName ************************************************
    If frmSpec!mNote = True Then
        '*********************************************************************************************************
        '*********************************************************************************************************
        'text = text & Chr(10) & "\Farial.ttf;\H8.0;" & RsCSI!mCSI & " " & RsCSI!MCSIname & "\P"
        '*********************************************************************************************************
        text = text & Chr(10) & "\Farial.ttf;\H" & xScF8 & ";" & RsCSI!mCSI & " " & RsCSI!MCSIname & "\P"
        '*********************************************************************************************************
        '*********************************************************************************************************
    Else
        text = text & Chr(10) & RsCSI!mCSI & " " & RsCSI!MCSIname & "\P"
    End If
'*********************** Format End CSIName ************************************************

    'Set MTextObj = ThisDrawing.ModelSpace.AddMText(corner, width, text)

    'UserForm1.TextBox1 = RsCSI!MCSI
    
    'strPpart = "SELECT PROJPART.PROJPARTID, PROJPART.PROJCSIID, PROJPART.PROJPARTNO, " _
    & "MPART.MPARTID, MPART.MPART FROM MPART INNER JOIN PROJPART ON PROJPART.MPARTID=mpart.MPARTID " _
    & "WHERE (((PROJPART.PROJCSIID)=" & xProjCSIID & "));"
    strPpart = "SELECT PROJPART.PROJPARTID, PROJPART.PROJCSIID, PROJPART.PROJPARTNO, MPART.MPARTID, MPART.MPART " _
    & "FROM MPART INNER JOIN PROJPART ON MPART.MPARTID = PROJPART.MPARTID " _
    & "WHERE (((PROJPART.PROJCSIID)=" & xProjCSIID & ")) " _
    & "ORDER BY PROJPART.PROJPARTNO;"

    Set RsPart = DB.OpenRecordset(strPpart)
        With RsPart
        .MoveFirst
        .MoveLast
        .MoveFirst

        rnPart = RsPart.RecordCount
        If rnPart > 0 Then
        
        Debug.Print "rnPart: " & rnPart
        
        'text = text & vbCrLf & RsPart!MPART
        'Set MTextObj = ThisDrawing.ModelSpace.AddMText(corner, width, text)

        'For iPart = 1 To rnPart
        For iPart = 1 To rnPart
        
            'UserForm1.TextBox1 = UserForm1.TextBox1 & vbCrLf & RsPart!MPART
            ' Creates the mtext Object
            'text = text & vbCrLf & RsPart!MPART
'*********************** Format Start Part ************************************************
            If frmSpec!mNote = True Then
                
                'text = text & "\P" & Chr(9) & RsPart!MPART & "\P"
                Debug.Print RsPart!MPART
                text = text
            Else
                text = text & "\P" & "PART " & RsPart!projpartno & Chr(9) & RsPart!MPART & "\P"
                'Set MTextObj = ThisDrawing.ModelSpace.AddMText(corner, width, text)
            End If
'*********************** Format End Part ************************************************

            xProjpartid = !projpartid
            strPat = "SELECT PROJAT.PROJATID, PROJAT.PROJPARTID, PROJAT.PROJATNO, " _
            & "MAT.MATID, MAT.MAT FROM MAT INNER JOIN PROJAT ON MAT.MATID=PROJAT.MATID " _
            & "WHERE (((PROJat.PROJpartid)=" & xProjpartid & ")) " _
            & "ORDER BY PROJAT.PROJATNO;"

            Set Rsat = DB.OpenRecordset(strPat, dbOpenDynaset)
                With Rsat
                If Rsat.RecordCount = 0 Then
                    GoTo ExitRsAt
                End If
                .MoveFirst
                .MoveLast
                .MoveFirst

                rnAt = Rsat.RecordCount
                If rnAt > 0 Then
                
                Debug.Print "rnat: " & rnAt
            
                For iat = 1 To rnAt
'*********************** Format Start AT ************************************************
            If frmSpec!mNote = True Then
                'text = text & "\P" & Rsat!projatno & Chr(46) & Chr(9) & UCase(Rsat!Mat) & "\P"
                '*********************************************************************************************************
                '*********************************************************************************************************
                'text = text & "\P" & "\Farial.ttf;\H6.0;" & mATno & Chr(46) & Chr(32) & Chr(32) & UCase(Rsat!Mat) '& "\P"
                '*********************************************************************************************************
                text = text & "\P" & "\Farial.ttf;\H" & xScF6 & ";" & mATno & Chr(46) & Chr(32) & Chr(32) & UCase(Rsat!Mat) '& "\P"
                '*********************************************************************************************************
                '*********************************************************************************************************
                mATno = mATno + 1
                
            Else
                text = text & "\P" & Rsat!projatno & Chr(46) & Chr(9) & UCase(Rsat!Mat) & "\P"
                'Set MTextObj = ThisDrawing.ModelSpace.AddMText(corner, width, text)
            End If
'*********************** Format End AT ************************************************

                    'UserForm1.TextBox1 = UserForm1.TextBox1 & vbCrLf & Chr(9) & RsAt!MAT
                    xProjatid = !projatid
                    
                    strPpara1 = "SELECT PROJPARA1.PROJPARA1ID, PROJPARA1.PROJATID, PROJPARA1.PROJPARA1NO, " _
                    & "MPARA1.MPARA1ID, MPARA1.MPARA1 FROM PROJPARA1 INNER JOIN MPARA1 ON PROJPARA1.MPARA1ID=MPARA1.MPARA1ID " _
                    & "WHERE (((PROJpara1.PROJatid)=" & xProjatid & ")) " _
                    & "ORDER BY PROJPARA1.PROJPARA1NO;"
                
                    Set Rspara1 = DB.OpenRecordset(strPpara1, dbOpenDynaset)
                        With Rspara1
                        If Rspara1.RecordCount = 0 Then
                            GoTo ExitPara1
                        End If
                        .MoveFirst
                        .MoveLast
                        .MoveFirst

                        rnPara1 = Rspara1.RecordCount
                        If rnPara1 > 0 Then
                            
                            For ipara1 = 1 To rnPara1
'*********************** Format Start P1 ************************************************
                                If frmSpec!mNote = True Then
                                    'SendKeys "%(09)"
                                    '*********************************************************************************************************
                                    '*********************************************************************************************************
                                    'text = text & "\P" & "\Fromans.shx;\H3.5;" & Chr(9) & Chr(45) & Chr(9) & UCase(Rspara1!Mpara1) & "\P"
                                    '*********************************************************************************************************
                                    text = text & "\P" & "\Fromans.shx;\H" & xScF4 & ";" & Chr(9) & Chr(45) & Chr(9) & UCase(Rspara1!Mpara1) & "\P"
                                    '*********************************************************************************************************
                                    '*********************************************************************************************************
                                    '*********************************************************************************************************
                                
                                Else
                                    text = text & "\P" & Chr(9) & Rspara1!projpara1no & Chr(46) & Chr(9) & UCase(Rspara1!Mpara1) & "\P"
                                'Set MTextObj = ThisDrawing.ModelSpace.AddMText(corner, width, text)
                                End If
'*********************** Format End P1 ************************************************
                                'UserForm1.TextBox1 = UserForm1.TextBox1 & vbCrLf & Chr(9) & Chr(9) & rsPara1!Mpara1
                                xProjpara1id = !projpara1id
                                
                                strPpara2 = "SELECT PROJPARA2.PROJPARA2ID, PROJPARA2.PROJPARA1ID, PROJPARA2.PROJPARA2NO,  MPARA2.MPARA2ID, " _
                                & "MPARA2.MPARA2 FROM PROJPARA2 INNER JOIN MPARA2 ON PROJPARA2.MPARA2ID=MPARA2.MPARA2ID " _
                                & "WHERE (((PROJpara2.PROJpara1id)=" & xProjpara1id & ")) " _
                                & "ORDER BY PROJPARA2.PROJPARA2id;"
                                '& "ORDER BY PROJPARA2.PROJPARA2id;"
                                '& "ORDER BY PROJPARA2.PROJPARA2NO;"
                                
                                'PROJPARA2.IIf([PROJPARA2NO] Is Null,0,Val([projpara2no])) AS PROJPARA2NOv,
                                
                                
                                Set rspara2 = DB.OpenRecordset(strPpara2, dbOpenDynaset)
                                With rspara2
                                If rspara2.RecordCount = 0 Then
                                    GoTo ExitPara2
                                End If
                                
                                rnpara2 = rspara2.RecordCount
                                '.Sort = "val[PROJPARA2.PROJPARA2no] asC"
                                If rnpara2 > 0 Then
                                .MoveFirst
                                .MoveLast
                                .MoveFirst
                                .Sort = "val[PROJPARA2.PROJPARA2no] asC"
                                    rnpara2 = rspara2.RecordCount
                                    For ipara2 = 1 To rnpara2
'*********************** Format Start P2 ************************************************
                                    If frmSpec!mNote = True Then
                                        text = text & "\P" & Chr(9) & Chr(9) & Chr(9) & Chr(9) & Chr(9) & Chr(45) & Chr(9) & UCase(rspara2!Mpara2) & "\P"
                                    Else
                                        text = text & "\P" & Chr(9) & Chr(9) & rspara2!PROJPARA2no & Chr(46) & Chr(9) & UCase(rspara2!Mpara2) & "\P"
                                        Debug.Print rspara2!PROJPARA2no
                                    End If
'*********************** Format End P2 ************************************************
                                        xProjpara2id = !projpara2id
                                '-------------------------------------------------------------------------
                                        strPpara3 = "SELECT PROJPARA3.PROJPARA3ID, PROJPARA3.PROJPARA2ID, PROJPARA3.PROJPARA3NO, MPARA3.MPARA3ID, " _
                                        & "MPARA3.MPARA3 FROM PROJPARA3 INNER JOIN MPARA3 ON PROJPARA3.MPARA3ID=MPARA3.MPARA3ID " _
                                        & "WHERE (((PROJpara3.PROJpara2id)=" & xProjpara2id & ")) " _
                                        & "ORDER BY PROJPARA3.PROJPARA3NO;"
                                        Set rspara3 = DB.OpenRecordset(strPpara3, dbOpenDynaset)
                                        
                                        
                                        With rspara3
                                        If rspara3.RecordCount = 0 Then
                                        GoTo ExitPara3
                                        End If
                                        .MoveFirst
                                        .MoveLast
                                        .MoveFirst

                                        rnpara3 = rspara3.RecordCount
                                        Debug.Print rnpara3
                                        If rnpara3 > 0 Then
                                            
                                            For ipara3 = 1 To rnpara3
'*********************** Format Start P3 ************************************************
                                                If frmSpec!mNote = True Then
                                                    text = text & "\P" & Chr(9) & Chr(9) & Chr(9) & Chr(9) & Chr(9) & Chr(9) & Chr(9) & Chr(9) & Chr(45) & Chr(9) & rspara3!Mpara3 & "\P"
                                                Else
                                                    text = text & "\P" & Chr(9) & Chr(9) & Chr(9) & rspara3!projpara3no & Chr(46) & Chr(9) & rspara3!Mpara3 & "\P"
                                                End If
'*********************** Format End P3 ************************************************
                                                Debug.Print ">>>projpara3id>>> "; !projpara3id
                                                xProjpara3id = !projpara3id
                                                If !projpara3id = 2147 Then
                                                Debug.Print ">>>>>>>>>>>>>>>>>>>>>>>>>>>>>>>>>>>> check"
                                                End If
                                '-------------------------------------------------------------------------
                                '-------------------------------------------------------------------------
                                                strPpara4 = "SELECT PROJPARA4.PROJPARA4ID, PROJPARA4.PROJPARA3ID, PROJPARA4.PROJPARA4NO, MPARA4.MPARA4ID, " _
                                                & "MPARA4.MPARA4 FROM PROJPARA4 INNER JOIN MPARA4 ON PROJPARA4.MPARA4ID=MPARA4.MPARA4ID " _
                                                & "WHERE (((PROJpara4.PROJpara3id)=" & xProjpara3id & ")) " _
                                                & "ORDER BY PROJPARA4.PROJPARA4NO;"
                                                Set rspara4 = DB.OpenRecordset(strPpara4, dbOpenDynaset)
                                
                                                With rspara4
                                                    If rspara4.RecordCount = 0 Then
                                                        GoTo ExitPara4
                                                    End If
                                                .MoveFirst
                                                .MoveLast
                                                .MoveFirst
        
                                                rnpara4 = rspara4.RecordCount
                                                If rnpara4 > 0 Then
                                                    
                                                    For ipara4 = 1 To rnpara4
                                                        text = text & "\P" & Chr(9) & Chr(9) & Chr(9) & Chr(9) & rspara4!projpara4no & Chr(46) & Chr(9) & rspara4!Mpara4 & "\P"
                                                        xProjpara4id = !projpara4id
                                                Debug.Print text
                                                        rspara4.MoveNext
                                                    Next ipara4
                                                End If
ExitPara4:
                                                End With 'rspara4
                                                rspara4.Close
                                '-------------------------------------------------------------------------
                                '-------------------------------------------------------------------------
                                                rspara3.MoveNext
                                            Next ipara3
                                        End If
ExitPara3:
                                        End With 'rspara3
                                        rspara3.Close
                        '-------------------------------------------------------------------------
                                        rspara2.MoveNext
                                    Next ipara2
                                    End If
                                    
ExitPara2:
                                End With 'rspara2
                                
                                rspara2.Close
                                
                                
                                
                        '-------------------------------------------------------------------------
                                
                                Rspara1.MoveNext
                            Next ipara1
                            End If
ExitPara1:
                        End With 'rspara1
                        Rspara1.Close
                    
                    '-------------------------------------------------------------------------
                    
                    Rsat.MoveNext
                    Next iat
                End If
ExitRsAt:
                End With 'rsat
                Rsat.Close
            
            '-------------------------------------------------------------------------
            RsPart.MoveNext
            Next iPart
            End If
ExitRsPart:
        End With 'rspart
        RsPart.Close
Next iCSI
Set mtextObj = ThisDrawing.ModelSpace.AddMText(corner, width, text)
If frmSpec!mNote = True Then
    CreateARstyle
    mtextObj.StyleName = "ar"
    mtextObj.height = 4
Else
    CreateCNstyle
    mtextObj.StyleName = "cn"
    mtextObj.height = 4
End If
mtextObj.Update
RsCSI.Close
End With 'rscsi

DB.Close


Debug.Print rnPart & rnAt & rnPara1
'Do Until RsPart.EOF = True

'    UserForm1.TextBox1 = RsPart!MPART
   ' RsPart.MoveNext
    
'Loop
'Exit_writemtext:
    'Exit Function

'Err_writemtext:
    'MsgBox Err.Description
    'Resume Exit_writemtext
End Function
Sub CreateCNstyle_spec()
Dim newText As AcadTextStyle
Dim blnFoundText As Boolean
Dim blnFoundTitle As Boolean
Dim blnFoundSub As Boolean
   
'reset blnFound
blnFoundText = False
blnFoundTitle = False
blnFoundSub = False

    For i = 0 To ThisDrawing.TextStyles.Count - 1  'make the styles for the form
        Debug.Print ThisDrawing.TextStyles(i).Name
        If ThisDrawing.TextStyles(i).Name = "CN" Then
            blnFoundText = True
            Exit Sub
        End If
        
    Next i

Set newText = ThisDrawing.TextStyles.Add("CN")

typeface = "Courier new"
newText.SetFont typeface, Bold, Italic, Charset, PitchandFamily

End Sub

Attribute VB_Name = "Mod_WallType"
Public Sub ShowProjWallType()
frmWallType.show
End Sub
Function writeProjENV(mProjEnvID As Integer)
'On Error GoTo Err_writemtext
Dim DB As Database
Dim rstProjBldgEnv, rstProjEnv, rstEnv, rstMAat, rstProjENVUA, rs As Recordset
Dim strProjBldgEnv, strProjEnv, strEnv, strMat, strProjENVUA As String
Dim rnProjBldgEnv, rnProjEnv, rnEnv, rnMat As Integer
Dim iProjBldgEnv, iProjEnv, iEnv, iMat  As Integer
Dim width As Double
Dim tmpEnvCategory As String
Dim MatArray() As Variant
'Dim StartPoint(0 To 2) As Double
'Dim SectionPoint(0 To 2) As Double
'Dim paraPoint(0 To 2) As Double
'Dim TextPosition(0 To 2) As Double
Dim TblPT(0 To 2) As Double
'Dim TblEndPT(0 To 2) As Double
'Dim SizestartPoint(0 To 2) As Double
'Dim width As Double
'Dim mATno As Integer

Dim txtHt As Double
Dim textObj As AcadText
Dim attributeObj As AcadAttribute


Dim nInspHeadDwg, nInspRowDwg As Variant
Dim nJumpHead, nJumpRow As Integer
Dim blockRefObj As AcadBlockReference
Dim BlkObj As Object
Dim k, l As Integer

'*********************************************************************************************
'*********************************************************************************************
Set DB = OpenDatabase("\\jwja-svr-10\jdb\DB_WALL\WALLASS03.mdb")
'*********************************************************************************************
'*********************************************************************************************
' 09/22/18
'*********************************************************************************************
'*********************************************************************************************
'mSCF= Scale Factor
If frmWallType.OptionButton1.value Then
    mSCF = 48 'mSCF= Scale Factor
    'width = mSCF * 8 '48 x 8 = 384
    width = mSCF * 7 '48 x 7 = 336
    xScF = mSCF / 12
ElseIf frmProjCode.OptionButton2.value Then
    mSCF = 96
    width = mSCF * 7 '96 x 8 = 768
    xScF = mSCF / 12
    xScFBig = xScF * 1.5
ElseIf frmProjCode.OptionButton3.value Then
    mSCF = 64
    width = mSCF * 7 '64 x 8 = 512
    xScF = mSCF / 12
ElseIf frmProjCode.OptionButton4.value Then
    mSCF = 128
    width = mSCF * 7 '64 x 8 = 512
    xScF = mSCF / 12
ElseIf frmProjCode.OptionButton5.value Then
    mSCF = 192
    width = mSCF * 7 '64 x 8 = 512
    xScF = mSCF / 12

End If
xScFBig = xScF * 1.5


    'mSCF = 48 'mSCF= Scale Factor
    'width = mSCF * 8 '48 x 8 = 384
    'width = 1440 * 6

'*********************************************************************************************
'*********************************************************************************************
'startPoint(0) = 0#: startPoint(1) = 0#: startPoint(2) = 0#
'SectionPoint(0) = 0#: SectionPoint(1) = 0#: SectionPoint(2) = 0#
'paraPoint(0) = 0#: paraPoint(1) = 0#: paraPoint(2) = 0#
'TextPosition(0) = 0#: TextPosition(1) = 0#: TextPosition(2) = 0#
'width = 384 '32' X 12'
TblPT(0) = 0: TblPT(1) = 0: TblPT(2) = 0

'codetext = ""
'mChapterNo = 1
'**********************************************************************************************************
'**********************************************************************************************************
mode = acAttributeModeVerify
nWTPROJENVHD = "\\jwja-svr-10\drawfile\jvba\XWTPROJENVHD.dwg"
nWTENVSUMHD = "\\jwja-svr-10\drawfile\jvba\XWTENVSUMHD.dwg"
nWTMATROW01 = "\\jwja-svr-10\drawfile\jvba\XWTMATROW01.dwg"
nWTENVSUMFOOT = "\\jwja-svr-10\drawfile\jvba\XWTENVSUMFOOT.dwg"
nWTPROJENVUAHD = "\\jwja-svr-10\drawfile\jvba\XWTPROJENVUAHD.dwg"
nWTPROJENVUArow = "\\jwja-svr-10\drawfile\jvba\XWTPROJENVUAROW.dwg"
nWTPROJENVUAFOOT = "\\jwja-svr-10\drawfile\jvba\XWTPROJENVUAFOOT.dwg"

nJumpPROJENVHD = 30 '2.5 X 12
nJumpENVsumHD = 24 '2 X 12
nJumpMATROW01 = 18 '1.5 X 12
nJumpEnvSumFoot = 30 '2.5 X 12
nJumpProjEnvUAHD = 42 '3.5 X 12
nJumpProjEnvUArow = 18 '1.5 X 12
nJumpPRJENVUAFOOT = 48 '4 X 12
nShift = 189 '15'-9x12
xProjEnvID = mProjEnvID
'CAD3
strProjEnvItem = "SELECT ConnProjBldgEnv.ProjBldgEnvid, ConnProjBldgEnv.ProjENvID, ProjEnvItem.ProjEnvNo, " _
    & "ProjEnvItem.ProjENvCategory, ProjEnvItem.ProjEnvType, ProjEnvItem.ProjENvKey,ProjEnvItem.ProjENvName,ProjEnvItem.ProjEnvArea, ProjEnvItem.ProjENvR, " _
    & "ProjEnvItem.ProjEnvU, ProjEnvItem.ProjUWt, ProjEnvItem.ProjRwt, ProjEnvItem.ProjEnvKey, ProjEnvItem.ProjComponentType, " _
    & "ProjEnvItem.ProjEnvUAdiff, ProjEnvItem.Utable, ProjEnvItem.ProjEnvUAtable, ProjEnvItem.ProjEnvFLdiff, ProjEnvItem.ProjEnvF, " _
    & "ProjEnvItem.ProjEnvFL, ProjEnvItem.ProjEnvFLtable, ProjEnvItem.Ftable, ProjEnvItem.ProjEnvCAdiff, ProjEnvItem.ProjEnvCA, " _
    & "ProjEnvItem.ProjEnvThick, ProjEnvItem.ProjEnvThickFrac, ProjEnvItem.ProjEnvNote, ProjEnvItem.ThermBrid, " _
    & "ProjEnvItem.ProjEnvAreaUnit, ProjEnvItem.ProjEnvUATotal, ProjEnvItem.CitationUtable " _
    & "FROM ProjEnvItem INNER JOIN ConnProjBldgEnv ON ProjEnvItem.ProjEnvID = ConnProjBldgEnv.ProjENvID " _
    & "WHERE (((ConnProjBldgEnv.ProjBldgEnvid)=" & xProjEnvID & ")) " _
    & "ORDER BY ProjEnvItem.ProjENvCategory, ProjEnvItem.ProjEnvType, ProjEnvItem.ProjEnvNo;"
'CAD5


        'strProjEnvItem = "SELECT ConnEnv.ConnEnvID, ConnEnv.EnvItemID, ConnEnv.ProjEnvID, ProjEnvItem.Proj_No, ProjEnvItem.ProjEnvNo, " _
        & "ProjEnvItem.ProjENvCategory, ProjEnvItem.ProjEnvType, ProjEnvItem.ProjENvName, ProjEnvItem.ProjEnvArea, ProjEnvItem.ProjENvR, " _
        & "ProjEnvItem.ProjEnvU, ProjEnvItem.ProjUWt, ProjEnvItem.ProjRwt, ProjEnvItem.ProjEnvKey, ProjEnvItem.ProjComponentType, " _
        & "ProjEnvItem.ProjEnvUAdiff, ProjEnvItem.Utable, ProjEnvItem.ProjEnvUAtable, ProjEnvItem.ProjEnvFLdiff, ProjEnvItem.ProjEnvF, " _
        & "ProjEnvItem.ProjEnvFL, ProjEnvItem.ProjEnvFLtable, ProjEnvItem.Ftable, ProjEnvItem.ProjEnvCAdiff, ProjEnvItem.ProjEnvCA, " _
        & "ProjEnvItem.ProjEnvThick, ProjEnvItem.ProjEnvThickFrac, ProjEnvItem.ProjEnvNote, ProjEnvItem.ThermBrid, " _
        & "ProjEnvItem.ProjEnvAreaUnit, ProjEnvItem.ProjEnvUATotal, ProjEnvItem.CitationUtable " _
        & "FROM ProjEnvItem INNER JOIN ConnEnv ON ProjEnvItem.ProjEnvID=ConnEnv.ProjEnvID  " _
        & "WHERE (ConnEnv.ProjEnvID)=" & xProjEnvID

Set rstProjEnvItem = DB.OpenRecordset(strProjEnvItem)
Debug.Print rstProjEnvItem.RecordCount
'rstProjEnvItem.MoveFirst
rstProjEnvItem.MoveLast
rstProjEnvItem.MoveFirst
If rstProjEnvItem.RecordCount = 0 Then
    GoTo Exit_writeProjENV
End If
nProjEnvItemRow = rstProjEnvItem.RecordCount
Debug.Print "nProjEnvItemRow:???? " & nProjEnvItemRow
With rstProjEnvItem ' With S 1
'%%%%%%%%%%%%%%%%%%%%%%%%%%%%%%%%%%%%%%%%%%%%%%%%%%%%%%%%%%%%%%%%%%%%%%%%%%%%%%%%%%
' Loop 1 Start

    'For k = 0 To nProjEnvItemRow - 1 'Loop 1
    Do While Not rstProjEnvItem.EOF 'Loop 1
        '==============================================
        mProjEnvID = !ProjEnvID
        'mEnvItemID = !EnvItemID
        '==============================================
'++++++++++++++++++++++++++++++++++++++++++++++++++++++++++++++++++++++++++++++++
'++++++++++++++++++++++++ 1 dwg +++++++++++++++++++++++++++++++++++++++++++++++++
'++++++++++++++++++++++++++++++++++++++++++++++++++++++++++++++++++++++++++++++++
        Set blockRefObj = ThisDrawing.ModelSpace.InsertBlock _
                 (TblPT, nWTPROJENVHD, 1, 1, 1, 0) 'First dwg
        TblPT(1) = TblPT(1) - nJumpPROJENVHD
        Dim varAttributes As Variant
        varAttributes = blockRefObj.GetAttributes
        '************ XPROJENVHD ***************************************************************
        
        
        For iattr_ProjEnvItem = LBound(varAttributes) To UBound(varAttributes)
            Debug.Print varAttributes(iattr_ProjEnvItem).TagString
            If varAttributes(iattr_ProjEnvItem).TagString = "XPROJENVHD" Then
                If IsNull(!ProjENvKey) = True Then
                    varAttributes(iattr_ProjEnvItem).textString = ""
                Else
                    varAttributes(iattr_ProjEnvItem).textString = !ProjENvKey
                    Debug.Print varAttributes(iattr_ProjEnvItem).textString
                End If
            End If
        '************ XPROJENVCATEGORY ***************************************************************
        'Dim rs As Recordset

    'sSQL = "SELECT [SC Date] FROM [Stock Conversion] WHERE SCID = " _
     & txtSCNumber.value
    sSQL = "SELECT [EnvCategory] FROM [EnvCategory] WHERE EnvCatID = " & !ProjENvCategory
    ' & txtSCNumber.value
     
    Set rs = DB.OpenRecordset(sSQL)
    tmpEnvCategory = rs![EnvCategory]

        'tmpEnvCategory = dlookup("EnvCategory", "EnvCategory", "[EnvCatID]=" & ProjENvCategory)
            If varAttributes(iattr_ProjEnvItem).TagString = "XENVCATEGORY" Then
                If IsNull(tmpEnvCategory) = True Then
                    varAttributes(iattr_ProjEnvItem).textString = ""
                Else
                    varAttributes(iattr_ProjEnvItem).textString = tmpEnvCategory
                    Debug.Print varAttributes(iattr_ProjEnvItem).textString
                End If
            End If
            rs.Close
        Set rs = Nothing
        
        '*********************************************************************************************
        Next iattr_ProjEnvItem
        
        
        '************ XENVHD ***************************************************************
        'mEnvItemID = !EnvItemID
        'strEnv = "SELECT EnvItem.EnvItemID, EnvItem.EnvItemKey, EnvItem.EnvItemName, EnvItem.EnvItemArea, EnvItem.EnvItemU, " _
        & "EnvItem.EnvItemNote, EnvItem.EnvCategory, EnvItem.EnvItemThick, EnvItem.EnvItemR, EnvItem.EnvItemThickFrac, EnvItem.ThermBrid, " _
        & "EnvItem.EnvItemLink, EnvItem.EnvTypeID " _
        & "FROM EnvItem " _
        & "WHERE (EnvItem.EnvItemID)=" & mEnvItemID
        
        'strEnv = "SELECT ConnEnv.ProjEnvID, ConnEnv.EnvItemID, EnvItem.EnvItemKey, EnvItem.EnvItemName, EnvItem.EnvItemArea, " _
        & "EnvItem.EnvItemU, EnvItem.EnvItemNote, EnvItem.EnvCategory, EnvItem.EnvItemThick, EnvItem.EnvItemR, EnvItem.EnvItemThickFrac, " _
        & "EnvItem.ThermBrid, EnvItem.EnvItemLink, EnvItem.EnvTypeID " _
        & "FROM EnvItem INNER JOIN ConnEnv ON EnvItem.EnvItemID = ConnEnv.EnvItemID " _
        & "WHERE (ConnEnv.ProjEnvID)=" & mProjEnvID
    
        'CAD5
        'strEnv = "SELECT ConnEnv.ConnEnvID, ConnEnv.EnvItemID, ConnEnv.ProjEnvID, ProjEnvItem.Proj_No, ProjEnvItem.ProjEnvNo, " _
        & "ProjEnvItem.ProjENvCategory, ProjEnvItem.ProjEnvType, ProjEnvItem.ProjENvName, ProjEnvItem.ProjEnvArea, ProjEnvItem.ProjENvR, " _
        & "ProjEnvItem.ProjEnvU, ProjEnvItem.ProjUWt, ProjEnvItem.ProjRwt, ProjEnvItem.ProjEnvKey, ProjEnvItem.ProjComponentType, " _
        & "ProjEnvItem.ProjEnvUAdiff, ProjEnvItem.Utable, ProjEnvItem.ProjEnvUAtable, ProjEnvItem.ProjEnvFLdiff, ProjEnvItem.ProjEnvF, " _
        & "ProjEnvItem.ProjEnvFL, ProjEnvItem.ProjEnvFLtable, ProjEnvItem.Ftable, ProjEnvItem.ProjEnvCAdiff, ProjEnvItem.ProjEnvCA, " _
        & "ProjEnvItem.ProjEnvThick, ProjEnvItem.ProjEnvThickFrac, ProjEnvItem.ProjEnvNote, ProjEnvItem.ThermBrid, " _
        & "ProjEnvItem.ProjEnvAreaUnit, ProjEnvItem.ProjEnvUATotal, ProjEnvItem.CitationUtable " _
        & "FROM ProjEnvItem INNER JOIN ConnEnv ON ProjEnvItem.ProjEnvID=ConnEnv.ProjEnvID  " _
        & "WHERE (ConnEnv.ProjEnvID)=" & mProjEnvID
        '+++++++++++++++++++++++++++++++++++++++++++++++++++++++++++++++++++++++++++++++++
        '+++++++++++++++++++++++++++++++++++++++++++++++++++++++++++++++++++++++++++++++++
        '+++++++++++++++++++++++++++++++++++++++++++++++++++++++++++++++++++++++++++++++++
       strEnv = "SELECT ConnEnv.ProjEnvID, ConnEnv.EnvItemID, EnvItem.EnvItemKey, EnvItem.EnvItemName, EnvItem.EnvItemArea, EnvItem.EnvItemU, " _
       & "EnvItem.EnvItemNote, EnvItem.EnvCategory, EnvItem.EnvItemThick, EnvItem.EnvItemR, EnvItem.EnvItemThickFrac, EnvItem.ThermBrid, " _
       & "EnvItem.EnvItemLink, EnvItem.EnvTypeID " _
        & "FROM EnvItem INNER JOIN ConnEnv ON EnvItem.EnvItemID = ConnEnv.EnvItemID " _
        & "WHERE (ConnEnv.ProjEnvID)=" & mProjEnvID
     
        
        Set rstEnv = DB.OpenRecordset(strEnv)
        Debug.Print "rstEnv Count: " & rstEnv.RecordCount
        With rstEnv ' With S 2
            '%%%%%%%%%%%%%%%%%%%%%%%%%%%%%%%%%%%%%%%%%%%%%%%%%%%%%%%%%%%%%%%%%%%%%%%%%%%%%%%%%%
            '%%%%%%%%%%%%%%%%%%%%%%%%%%%%%%%%%%%%%%%%%%%%%%%%%%%%%%%%%%%%%%%%%%%%%%%%%%%%%%%%%%
            Do While Not rstEnv.EOF 'Loop 2
            mEnvItemID = !EnvItemID
'++++++++++++++++++++++++++++++++++++++++++++++++++++++++++++++++++++++++++++++++
'++++++++++++++++++++++++ 2 dwg +++++++++++++++++++++++++++++++++++++++++++++++++
'++++++++++++++++++++++++++++++++++++++++++++++++++++++++++++++++++++++++++++++++
            Set blockRefObj = ThisDrawing.ModelSpace.InsertBlock _
                     (TblPT, nWTENVSUMHD, 1, 1, 1, 0) 'Second dwg
            TblPT(1) = TblPT(1) - nJumpENVsumHD
            Dim varAttributes1 As Variant
            varAttributes1 = blockRefObj.GetAttributes
            '{{{{{{{{{{{{{{{{{{{{{{{{{{{{{{{{{{{{{{{{{{{{{{{{{{{{{{{{{{{{{{{{{{{{{{{{{{{
                For iattr_EnvItem = LBound(varAttributes1) To UBound(varAttributes1)
                    Debug.Print varAttributes1(iattr_EnvItem).TagString
                    If varAttributes1(iattr_EnvItem).TagString = "XENVitemKey" Then
                        If IsNull(!ENVItemKey) = True Then
                            varAttributes1(iattr_EnvItem).textString = ""
                        Else
                            varAttributes1(iattr_EnvItem).textString = !ENVItemKey
                            Debug.Print varAttributes1(iattr_EnvItem).textString
                        End If
                    End If
                    Debug.Print !EnvItemName
                    If varAttributes1(iattr_EnvItem).TagString = "XENVSUMNAME" Then
                        If IsNull(!EnvItemName) = True Then
                            varAttributes1(iattr_EnvItem).textString = ""
                        Else
                            varAttributes1(iattr_EnvItem).textString = !EnvItemName
                            Debug.Print varAttributes1(iattr_EnvItem).textString
                        End If
                    End If
                    '+++++++++++++++++++++++++++++++++++++++++++++++++++++++++++++++++++++++++++++++++
                    '+++++++++++++++++++++++++++++++++++++++++++++++++++++++++++++++++++++++++++++++++
                    '+++++++++++++++++++++++++++++++++++++++++++++++++++++++++++++++++++++++++++++++++
                    '+++++++++++++++++++++++++++++++++++++++++++++++++++++++++++++++++++++++++++++++++
                    mEnvItemID = !EnvItemID
                    Debug.Print "mEnvItemID: " & mEnvItemID
                    strMat = "SELECT ConnMat.ConnMatID, ConnMat.MatID, ConnMat.EnvItemID, ConnMat.Order, Material.MatCategory, Material.MatDiv, Material.MatType, Material.MatKey, " _
                    & "Material.MatName, Material.MatThick, Material.MatR, Material.MatU, Material.MatMFGR, Material.MatNote, Material.MatLink, Material.ThermBrid, " _
                    & "Material.MatRu, Material.MatHC, Material.MatC, Material.MatF, Material.MatSHGC, Material.MatAirLeak " _
                    & "FROM Material INNER JOIN ConnMat ON Material.MatID = ConnMat.MatID " _
                    & "WHERE ((ConnMat.EnvItemID)=" & mEnvItemID & ")" _
                    & "ORDER BY ConnMat.Order "
                
                    
                    Set rstMat = DB.OpenRecordset(strMat)
                    With rstMat ' With S 3
                    '%%%%%%%%%%%%%%%%%%%%%%%%%%%%%%%%%%%%%%%%%%%%%%%%%%%%%%%%%%%%%%%%%%%%%%%%%%%%%%%%%%
                    '%%%%%%%%%%%%%%%%%%%%%%%%%%%%%%%%%%%%%%%%%%%%%%%%%%%%%%%%%%%%%%%%%%%%%%%%%%%%%%%%%%
                    '%%%%%%%%%%%%%%%%%%%%%%%%%%%%%%%%%%%%%%%%%%%%%%%%%%%%%%%%%%%%%%%%%%%%%%%%%%%%%%%%%%
                        Do While Not rstMat.EOF 'Loop 3
                        Debug.Print "rstMat Record Count:>>>>>>>" & rstMat.RecordCount
'++++++++++++++++++++++++++++++++++++++++++++++++++++++++++++++++++++++++++++++++
'++++++++++++++++++++++++ 3 dwg +++++++++++++++++++++++++++++++++++++++++++++++++
'++++++++++++++++++++++++++++++++++++++++++++++++++++++++++++++++++++++++++++++++
                            Set blockRefObj = ThisDrawing.ModelSpace.InsertBlock _
                                 (TblPT, nWTMATROW01, 1, 1, 1, 0) 'Third dwg
                        Dim varAttributes2 As Variant
                        varAttributes2 = blockRefObj.GetAttributes
                        
                        '{{{{{{{{{{{{{{{{{{{{{{{{{{{{{{{{{{{{{{{{{{{{{{{{{{{{{{{{{{{{{{{{{{{{{{{{{{{
                                For iattr_Mat = LBound(varAttributes2) To UBound(varAttributes2)
                                '************ XMAT ***************************************************************
                                    If varAttributes2(iattr_Mat).TagString = "XMAT" Then
                                        If IsNull(!MatName) = True Then
                                            varAttributes2(iattr_Mat).textString = ""
                                        Else
                                            varAttributes2(iattr_Mat).textString = !MatName
                                            Debug.Print varAttributes2(iattr_Mat).textString
                                        End If
                                    End If
                                '************ XMATR ***************************************************************
                                    If varAttributes2(iattr_Mat).TagString = "XMATR" Then
                                        If IsNull(!matr) = True Then
                                            varAttributes2(iattr_Mat).textString = ""
                                        Else
                                            varAttributes2(iattr_Mat).textString = !matr
                                            Debug.Print varAttributes2(iattr_Mat).textString
                                        End If
                                    End If
                                '************ XMATNOTE1 ***************************************************************
                                    If varAttributes2(iattr_Mat).TagString = "XMATNOTE1" Then
                                        If IsNull(!MatNote) = True Then
                                            varAttributes2(iattr_Mat).textString = ""
                                        Else
                                            varAttributes2(iattr_Mat).textString = SEPTEXT2(!MatNote, 1, 2, 12)
                                            'varAttributes1(iattr_Insp).textString = SEPTEXT2(!ENERGYWORKSCOPE, 1, 2, 40)
                                            Debug.Print varAttributes2(iattr_Mat).textString
                                        End If
                                    End If
                                '************ XMATNOTE1 ***************************************************************
                                    If varAttributes2(iattr_Mat).TagString = "XMATNOTE2" Then
                                        If IsNull(!MatNote) = True Then
                                            varAttributes2(iattr_Mat).textString = ""
                                        Else
                                            varAttributes2(iattr_Mat).textString = SEPTEXT2(!MatNote, 2, 2, 12)
                                            'varAttributes1(iattr_Insp).textString = SEPTEXT2(!ENERGYWORKSCOPE, 1, 2, 40)
                                            Debug.Print varAttributes2(iattr_Mat).textString
                                        End If
                                    End If
                                '.MoveNext
                                Next iattr_Mat
                            '}}}}}}}}}}}}}}}}}}}}}}}}}}}}}}}}}}}}}}}}}}}}}}}}}}}}}}}}}}}}}}}}}}}}}}}}}}}}}}}}}}
                            rstMat.MoveNext
                            TblPT(1) = TblPT(1) - nJumpMATROW01
                            Loop 'Loop 3
                    '%%%%%%%%%%%%%%%%%%%%%%%%%%%%%%%%%%%%%%%%%%%%%%%%%%%%%%%%%%%%%%%%%%%%%%%%%%%%%%%%%%
                    '%%%%%%%%%%%%%%%%%%%%%%%%%%%%%%%%%%%%%%%%%%%%%%%%%%%%%%%%%%%%%%%%%%%%%%%%%%%%%%%%%%
                    '%%%%%%%%%%%%%%%%%%%%%%%%%%%%%%%%%%%%%%%%%%%%%%%%%%%%%%%%%%%%%%%%%%%%%%%%%%%%%%%%%%
                    End With 'rstMAT ' With e 3
                    rstMat.Close
                    Set rstMat = Nothing
                    '+++++++++++++++++++++++++++++++++++++++++++++++++++++++++++++++++++++++++++++++++
                    '+++++++++++++++++++++++++++++++++++++++++++++++++++++++++++++++++++++++++++++++++
                    '+++++++++++++++++++++++++++++++++++++++++++++++++++++++++++++++++++++++++++++++++
                    '+++++++++++++++++++++++++++++++++++++++++++++++++++++++++++++++++++++++++++++++++
             'rstEnv.MoveNext
             'Loop 'Loop 3
                 
            Next iattr_EnvItem 'SECOND DWG END
            '}}}}}}}}}}}}}}}}}}}}}}}}}}}}}}}}}}}}}}}}}}}}}}}}}}}}}}}}}}}}}}}}}}}}}}}}}}}}
            'rstEnv.MoveNext
            'Loop 'Loop 2
'++++++++++++++++++++++++++++++++++++++++++++++++++++++++++++++++++++++++++++++++
'++++++++++++++++++++++++ 4 dwg +++++++++++++++++++++++++++++++++++++++++++++++++
'++++++++++++++++++++++++++++++++++++++++++++++++++++++++++++++++++++++++++++++++
        Set blockRefObj = ThisDrawing.ModelSpace.InsertBlock _
                 (TblPT, nWTENVSUMFOOT, 1, 1, 1, 0) 'Fourth dwg
        Dim varAttributes3 As Variant
        varAttributes3 = blockRefObj.GetAttributes
        TblPT(1) = TblPT(1) - nJumpEnvSumFoot
        For i3 = LBound(varAttributes3) To UBound(varAttributes3)
            'For iattr_Mat = LBound(varAttributes2) To UBound(varAttributes2)
            'For iattr_EnvItem = LBound(varAttributes1) To UBound(varAttributes1)
        
            '************ XENVSUMRFOOT ***************************************************************
            If varAttributes3(i3).TagString = "XENVSUMRFOOT" Then
                If IsNull(!EnvItemName) = True Then
                    varAttributes3(i3).textString = ""
                Else
                    varAttributes3(i3).textString = "Total R-Value of " & !EnvItemName
                    Debug.Print varAttributes3(i3).textString
                End If
            End If
            '************ XENVSUMUFOOT ***************************************************************
            If varAttributes3(i3).TagString = "XENVSUMUFOOT" Then
                If IsNull(!EnvItemName) = True Then
                    varAttributes3(i3).textString = ""
                Else
                    varAttributes3(i3).textString = "U-Factor of " & !EnvItemName
                    Debug.Print varAttributes3(i3).textString
                End If
            End If
            
            '************ XENVSUMR ***************************************************************
            If varAttributes3(i3).TagString = "XENVSUMR" Then
                If IsNull(!EnvItemR) = True Then
                    varAttributes3(i3).textString = ""
                Else
                    varAttributes3(i3).textString = !EnvItemR
                    Debug.Print varAttributes3(i3).textString
                End If
            End If
            '************ XENVSUMU ***************************************************************
            If varAttributes3(i3).TagString = "XENVSUMU" Then
                If IsNull(!EnvItemU) = True Then
                    varAttributes3(i3).textString = ""
                Else
                    varAttributes3(i3).textString = !EnvItemU
                    Debug.Print varAttributes3(i3).textString
                End If
            End If
            '************ XENVSUMNOTE1 ***************************************************************
            If varAttributes3(i3).TagString = "XENVSUMNOTE1" Then
                If IsNull(!EnvItemNote) = True Then
                    varAttributes3(i3).textString = ""
                Else
                    varAttributes3(i3).textString = SEPTEXT2(!EnvItemNote, 1, 4, 40)
                    Debug.Print varAttributes3(i3).textString
                End If
            End If
            '************ XENVSUMNOTE2 ***************************************************************
            If varAttributes3(i3).TagString = "XENVSUMNOTE2" Then
                If IsNull(!EnvItemNote) = True Then
                    varAttributes3(i3).textString = ""
                Else
                    varAttributes3(i3).textString = SEPTEXT2(!EnvItemNote, 2, 4, 40)
                    Debug.Print varAttributes3(i3).textString
                End If
            End If
            '************ XENVSUMNOTE3 ***************************************************************
            If varAttributes3(i3).TagString = "XENVSUMNOTE3" Then
                If IsNull(!EnvItemNote) = True Then
                    varAttributes3(i3).textString = ""
                Else
                    varAttributes3(i3).textString = SEPTEXT2(!EnvItemNote, 3, 4, 40)
                    Debug.Print varAttributes3(i3).textString
                End If
            End If
            '************ XENVSUMNOTE4 ***************************************************************
            If varAttributes3(i3).TagString = "XENVSUMNOTE4" Then
                If IsNull(!EnvItemNote) = True Then
                    varAttributes3(i3).textString = ""
                Else
                    varAttributes3(i3).textString = SEPTEXT2(!EnvItemNote, 4, 4, 40)
                    Debug.Print varAttributes3(i3).textString
                End If
            End If
        Next i3
    rstEnv.MoveNext
    Loop 'Loop 2 End 4th. dwg
    End With
'++++++++++++++++++++++++++++++++++++++++++++++++++++++++++++++++++++++++++++++++
'++++++++++++++++++++++++ 5 dwg +++++++++++++++++++++++++++++++++++++++++++++++++
'++++++++++++++++++++++++++++++++++++++++++++++++++++++++++++++++++++++++++++++++
        strProjENVUA = "SELECT EnvItem.EnvItemID, EnvItem.EnvItemKey, EnvItem.EnvItemName, EnvItem.EnvItemArea, EnvItem.EnvItemU, EnvItem.EnvItemNote, " _
        & "EnvItem.EnvCategory, EnvItem.EnvItemThick, EnvItem.EnvItemR, EnvItem.EnvItemThickFrac, EnvItem.ThermBrid, EnvItem.EnvItemLink, EnvItem.EnvTypeID, " _
        & "ProjEnvUA.ProjEnvID, ProjEnvUA.ProjBldgEnvID, ProjEnvUA.ProjEnvUA, ProjEnvUA.ProjEnvArea, ProjEnvUA.ProjEnvAreaUnit " _
        & "FROM (EnvItem INNER JOIN ProjEnvUA ON EnvItem.EnvItemID = ProjEnvUA.EnvItemID) INNER JOIN ConnEnv ON EnvItem.EnvItemID = ConnEnv.EnvItemID " _
        & "WHERE (ProjEnvUA.ProjEnvID)=" & mProjEnvID
        '& "WHERE (EnvItem.EnvItemID)=" & mEnvItemID
        '& "WHERE (ProjEnvUA.ProjEnvID)=" & mProjEnvID
        
        Set rstProjENVUA = DB.OpenRecordset(strProjENVUA)
        Debug.Print " rstProjENVUA : " & rstProjENVUA.RecordCount
        If rstProjENVUA.RecordCount = 0 Then
        GoTo skipProjUA
        Else
        With rstProjENVUA ' With S 4
            '%%%%%%%%%%%%%%%%%%%%%%%%%%%%%%%%%%%%%%%%%%%%%%%%%%%%%%%%%%%%%%%%%%%%%%%%%%%%%%%%%%
            '%%%%%%%%%%%%%%%%%%%%%%%%%%%%%%%%%%%%%%%%%%%%%%%%%%%%%%%%%%%%%%%%%%%%%%%%%%%%%%%%%%
            '%%%%%%%%%%%%%%%%%%%%%%%%%%%%%%%%%%%%%%%%%%%%%%%%%%%%%%%%%%%%%%%%%%%%%%%%%%%%%%%%%%
                           
            Set blockRefObj = ThisDrawing.ModelSpace.InsertBlock _
                             (TblPT, nWTPROJENVUAHD, 1, 1, 1, 0) 'Fifth dwg
            TblPT(1) = TblPT(1) - nJumpProjEnvUAHD
            Dim varAttributes4 As Variant
            varAttributes4 = blockRefObj.GetAttributes
            For i4 = LBound(varAttributes4) To UBound(varAttributes4)
                If varAttributes4(i4).TagString = "XPROJUAHDNOTE1" Then
                    If IsNull(!EnvItemNote) = True Or !EnvItemNote = "" Then
                        varAttributes4(i4).textString = ""
                    Else
                        varAttributes4(i4).textString = SEPTEXT2(!EnvItemNote, 1, 1, 40)
                        Debug.Print varAttributes4(i4).textString
                    End If
                End If
                If varAttributes4(i4).TagString = "XPROJUNITTYPE" Then
                    If IsNull(!ProjEnvAreaUnit) = True Then
                        varAttributes4(i4).textString = ""
                    Else
                        varAttributes4(i4).textString = "(" & !ProjEnvAreaUnit & ")"
                        Debug.Print varAttributes4(i4).textString
                    End If
                End If
                If varAttributes4(i4).TagString = "XPROJENVHD" Then
                    If IsNull(!EnvItemName) = True Then
                        varAttributes4(i4).textString = ""
                    Else
                        varAttributes4(i4).textString = !EnvItemName
                        Debug.Print varAttributes4(i4).textString
                    End If
                End If
            Next i4
            
            
                  
            
    '++++++++++++++++++++++++++++++++++++++++++++++++++++++++++++++++++++++++++++++++
    '++++++++++++++++++++++++ 6 dwg +++++++++++++++++++++++++++++++++++++++++++++++++
    '++++++++++++++++++++++++++++++++++++++++++++++++++++++++++++++++++++++++++++++++
            Do While Not rstProjENVUA.EOF 'Loop 999
            Set blockRefObj = ThisDrawing.ModelSpace.InsertBlock _
                     (TblPT, nWTPROJENVUArow, 1, 1, 1, 0) '6TH dwg
            TblPT(1) = TblPT(1) - nJumpProjEnvUArow
            Dim varAttributes5 As Variant
            varAttributes5 = blockRefObj.GetAttributes
            For i5 = LBound(varAttributes5) To UBound(varAttributes5)
                '************ XENVSUMNAME ***************************************************************
                If varAttributes5(i5).TagString = "XENVSUMNAME" Then
                    If IsNull(!EnvItemName) = True Then
                        varAttributes5(i5).textString = ""
                    Else
                        varAttributes5(i5).textString = !EnvItemName
                        Debug.Print varAttributes5(i5).textString
                    End If
                End If
                '************ PEU ***************************************************************
                If varAttributes5(i5).TagString = "PEU" Then
                    If IsNull(!EnvItemU) = True Then
                        varAttributes5(i5).textString = ""
                    Else
                        varAttributes5(i5).textString = !EnvItemU
                        Debug.Print varAttributes3(i5).textString
                    End If
                End If
                '************ PEA ***************************************************************
                If varAttributes5(i5).TagString = "PEA" Then
                    If IsNull(!ProjEnvArea) = True Then
                        varAttributes5(i5).textString = ""
                    Else
                        varAttributes5(i5).textString = !ProjEnvArea
                        Debug.Print varAttributes3(i5).textString
                    End If
                End If
                
                '************ UA -> ProjEnvUA ***************************************************************
                If varAttributes5(i5).TagString = "PEUA" Then
                    If IsNull(!ProjEnvUA) = True Then
                        varAttributes5(i5).textString = ""
                    Else
                        varAttributes5(i5).textString = !ProjEnvUA
                        Debug.Print varAttributes3(i5).textString
                    End If
                End If
            Next i5
            
            
            .MoveNext
            Loop 'lOOP 999
        End With ' With e 4
        End If
'skipProjUA:
    'rstProjEnvItem.MoveNext
'%%%%%%%%%%%%%%%%%%%%%%%%%%%%%%%%%%%%%%%%%%%%%%%%%%%%%%%%%%%%%%%%%%%%%%%%%%%%%%%%%%
Debug.Print "rstProjEnvItem.RecordCount:" & rstProjEnvItem.RecordCount
Debug.Print rstProjEnvItem.Fields("projenvarea")
    '++++++++++++++++++++++++++++++++++++++++++++++++++++++++++++++++++++++++++++++++
    '++++++++++++++++++++++++ 7 dwg +++++++++++++++++++++++++++++++++++++++++++++++++
    '++++++++++++++++++++++++++++++++++++++++++++++++++++++++++++++++++++++++++++++++
    Set blockRefObj = ThisDrawing.ModelSpace.InsertBlock _
             (TblPT, nWTPROJENVUAFOOT, 1, 1, 1, 0) '7TH dwg
    TblPT(1) = TblPT(1) - nJumpProjEnvUAFOOT
    Dim varAttributes6 As Variant
    varAttributes6 = blockRefObj.GetAttributes
    For i6 = LBound(varAttributes6) To UBound(varAttributes6)
        '************ PEU ***************************************************************
        If varAttributes6(i5).TagString = "PEU" Then
            If IsNull(!EnvItemU) = True Then
                varAttributes6(i6).textString = ""
            Else
                varAttributes6(i6).textString = !EnvItemU
                Debug.Print varAttributes5(i6).textString
            End If
        End If
        '************ PEASUM ***************************************************************
        If varAttributes6(i6).TagString = "PEASUM" Then
            If IsNull(!ProjEnvArea) = True Or !ProjEnvArea = "" Then
                varAttributes6(i6).textString = ""
            Else
                varAttributes6(i6).textString = !ProjEnvArea
                Debug.Print varAttributes6(i6).textString
            End If
        End If
        '************ PEUASUM ***************************************************************
        If varAttributes6(i6).TagString = "PEUASUM" Then
            If IsNull(!ProjEnvUATotal) = True Then
                varAttributes6(i6).textString = ""
            Else
                varAttributes6(i6).textString = !ProjEnvUATotal
                Debug.Print varAttributes6(i6).textString
            End If
        End If
        '************ PEUAFIN ***************************************************************
        If varAttributes6(i6).TagString = "PEUAFIN" Then
            If IsNull(!ProjEnvU) = True Then
                varAttributes6(i6).textString = ""
            Else
                varAttributes6(i6).textString = !ProjEnvU
                Debug.Print varAttributes6(i6).textString
            End If
        End If
        '************ PEUAFINCAL ***************************************************************
        If varAttributes6(i6).TagString = "PEUAFINCAL" Then
            If IsNull(!ProjEnvU) = True Then
                varAttributes6(i6).textString = ""
            Else
                varAttributes6(i6).textString = !ProjEnvUATotal & "/" & !ProjEnvArea & "="
                Debug.Print varAttributes6(i6).textString
            End If
        End If
        '************ UTABLE ***************************************************************
        If varAttributes6(i6).TagString = "UTABLE" Then
            If IsNull(!UTABLE) = True Then
                varAttributes6(i6).textString = ""
            Else
                varAttributes6(i6).textString = !UTABLE
                Debug.Print varAttributes6(i6).textString
            End If
        End If
        '************ UTABLECITATION ***************************************************************
        If varAttributes6(i6).TagString = "UTABLECITATION" Then
            If IsNull(!CitationUtable) = True Then
                varAttributes6(i6).textString = ""
            Else
                
                varAttributes6(i6).textString = "(" & !CitationUtable & ")"
                Debug.Print varAttributes6(i6).textString
            End If
        End If
        
    Next i6
skipProjUA:
    rstProjEnvItem.MoveNext
 TblPT(0) = TblPT(0) + nShift: TblPT(1) = 0
Loop

End With


Exit_writeProjENV:
rstProjEnvItem.Close
Set rstProjEnvItem = Nothing

End Function

Attribute VB_Name = "REF_FORMAT_MTEXT"
'https://knowledge.autodesk.com/search-result/caas/CloudHelp/cloudhelp/2015/ENU/AutoCAD-ActiveX/files/GUID-A43040EF-F9C5-4AEF-B87B-375FB16C77F2-htm.html
Sub Ch4_FormatMText()
  Dim mtextObj As AcadMText
  Dim insertPoint(0 To 2) As Double
  Dim width As Double
  Dim textString As String

  insertPoint(0) = 2
  insertPoint(1) = 2
  insertPoint(2) = 0
  width = 4

  ' Define the ASCII characters for the control characters
  Dim OB As Long  ' Open Bracket  {
  Dim CB As Long  ' Close Bracket }
  Dim BS As Long  ' Back Slash    \
  Dim FS As Long  ' Forward Slash /
  Dim SC As Long  ' Semicolon     ;
  OB = Asc("{")
  CB = Asc("}")
  BS = Asc("\")
  FS = Asc("/")
  SC = Asc(";")

  ' Assign the text string the following line of control
  ' characters and text characters:
  ' {{\H1.5x; Big text}\A2; over text\A1;/\A0; under text}

  textString = Chr(OB) + Chr(OB) + Chr(BS) + "H1.5x" _
  + Chr(SC) + "Big text" + Chr(CB) + Chr(BS) + "A2" _
  + Chr(SC) + "over text" + Chr(BS) + "A1" + Chr(SC) _
  + Chr(FS) + Chr(BS) + "A0" + Chr(SC) + "under text" _
  + Chr(CB)

  ' Create a text Object in model space
  Set mtextObj = ThisDrawing.ModelSpace.AddMText(insertPoint, width, textString)
  ZoomAll
End Sub

Function BigText(xText, xScFBig As Variant)
Dim textString As String
  ' Define the ASCII characters for the control characters
  Dim OB As Long  ' Open Bracket  {
  Dim CB As Long  ' Close Bracket }
  Dim BS As Long  ' Back Slash    \
  Dim FS As Long  ' Forward Slash /
  Dim SC As Long  ' Semicolon     ;
  OB = Asc("{")
  CB = Asc("}")
  BS = Asc("\")
  FS = Asc("/")
  SC = Asc(";")

  ' Assign the text string the following line of control
  ' characters and text characters:
  ' {{\H1.5x; Big text}\A2; over text\A1;/\A0; under text}
'BigText = Chr(OB) + Chr(OB) + Chr(BS) + "H1.2x" _
  + Chr(SC) + Chr(9) + Chr(9) + Chr(9) + Chr(9) + Chr(9) + Chr(9) + Chr(9) + xText + Chr(CB) + Chr(BS) + "A" _
  + Chr(SC) _
  + Chr(CB)
  'xScFBig not used
  BigText = Chr(OB) + Chr(OB) + Chr(BS) + "H" & 1.2 & "x" _
  + Chr(SC) + Chr(9) + Chr(9) + Chr(9) + Chr(9) + Chr(9) + Chr(9) + Chr(9) + xText + Chr(CB) + Chr(BS) + "A" _
  + Chr(SC) _
  + Chr(CB)

End Function

Attribute VB_Name = "SepText"
Function SEPTEXT(xText As String, ATno As Integer, lNo As Integer, tNo As Integer)
Dim strArray() As String
'Dim strData(0) As String
Dim strType() As String
Dim strLen() As Integer
Dim mType, tn As Variant
Dim strTimeStamp, srchChar1, srchChar2, srchChar3, xstrArray As String
Dim pos, txLen, xtNo, xSp, sp, sl, m, n, k, i, j, xstrLen As Integer
Dim blCutLast, blSl, blSp As Boolean

srchChar1 = Chr(32) '32 is space 45 => -, 47 => /
srchChar2 = Chr(45)
srchChar3 = Chr(47)

'strData(0) = xTEXT
pos = 1
sp = 0
sl = 0
If IsNull(xText) = True Then
    Exit Function
End If
Debug.Print Len(xText)
txLen = Len(xText)
If txLen = 0 Then
    Exit Function
End If


If txLen < tNo Then
    If ATno = 1 Then
    'SEPTEXT = ""
        SEPTEXT = xText
        Debug.Print "SEPTEXT @ SMALL tNo:" & SEPTEXT
    Else
        SEPTEXT = ""
    End If
    Exit Function
End If
' *************** Find space
If InStr(xText, srchChar1) <> 0 Then
    blSp = True
    For m = 1 To txLen
        If Mid(xText, m, 1) = srchChar1 Then
            sp = sp + 1
            blSp = True
        End If
    Next m
    ReDim strArray(sp + 1)
    Debug.Print "strArray(sp+1): " & strArray(sp + 1)
    ReDim strLen(sp + 1)
    Debug.Print "strLen(sp+1): " & strLen(sp + 1)
End If


If InStr(xText, srchChar2) <> 0 Then
    blSl = True
    For n = 1 To txLen
        If Mid(xText, n, 1) = srchChar2 Then
            sl = sl + 1
            blSl = True
        End If
    Next n
End If



Debug.Print "Total sp: " & sp & "Total sl: " & sl

xtNo = txLen / lNo 'MAX LINE NO?
xtNo = CInt(xtNo)
Debug.Print "xtNo: " & xtNo
If xtNo > tNo Then 'tNo = max text length variable
    blCutLast = True
End If


If blSp = True Then
    For i = 1 To sp + 1
    If i = lNo Then
        strArray(i) = Mid(xText, 1, txLen)
        xText = ""
        GoTo checkcomb
    Else
        xSp = InStr(xText, srchChar1)
        If xSp <> 0 Then
           strArray(i) = Mid(xText, 1, xSp)
        Else
           strArray(i) = Mid(xText, 1, txLen)
        End If
        
        strLen(i) = Len(strArray(i))
        xText = Mid(xText, xSp + 1, txLen)
    End If
    Debug.Print i & ": " & strArray(i)
    Next i
End If
checkcomb:
Debug.Print i & "<<<< i"
'If i - 1 > lNo Then ' combine text
If i > lNo Then  ' combine text
    For j = 1 To sp + 1
        If j = 1 Then
            xstrArray = ""
            xstrLen = 0
            GoTo NEXTj
        End If
        If xstrLen + strLen(i) > tNo Then
            strArray(i) = xstrArray & strArray(i)
        End If
NEXTj:
        
    Next j
    xstrArray = strArray(i)
        xstrLen = strLen(i)
End If
setText:
For k = 1 To lNo
    If k = ATno Then
        If k = lNo And blCutLast = True Then
            SEPTEXT = Mid(strArray(k), 1, tNo)
            Exit Function
        End If
    
    SEPTEXT = strArray(k)
    End If
Next k
Erase strArray, strLen, strType 'Jin added this line 10/21/12
Debug.Print SEPTEXT

End Function
Function SEPTEXT2(xText As String, ATno As Integer, lNo As Integer, tNo As Integer)
Dim strArray() As String
'Dim strData(0) As String
Dim strType() As String
Dim strLen() As Integer
Dim posSpace() As Integer
Dim posSlash() As Integer
Dim mType, tn As Variant
Dim strTimeStamp, srchChar1, srchChar2, srchChar3, xstrArray As String
Dim pos, txLen, xtNo, xSp, sp, sl, m, n, k, i, j, xstrLen, position As Integer
Dim blCutLast, blSl, blSp As Boolean

srchChar1 = Chr(32) '32 is space 45 => -, 47 => /
srchChar2 = Chr(47)
srchChar3 = Chr(45)
'++++++++++++++++++++++++++++++++
'xTEXT = Forms!frmtest!Text
'ATno = Forms!frmtest!lineno
'lNo = Forms!frmtest!linetotal
'tNo = Forms!frmtest!chrperline
'++++++++++++++++++++++++++++++++


'strData(0) = xTEXT
pos = 1
sp = 0
sl = 0
If IsNull(xText) = True Then
    Exit Function
End If
If xText = "" Then
    Exit Function
End If

Debug.Print Len(xText)
txLen = Len(xText)
If txLen = 0 Then
    Exit Function
End If


If txLen < tNo Then
    If ATno = 1 Then
    'SEPTEXT = ""
        SEPTEXT2 = xText
        Debug.Print "SEPTEXT @ SMALL tNo:" & SEPTEXT2
    Else
        SEPTEXT2 = ""
    End If
    Exit Function
End If
'****************************************************************
'***************  Find space      *******************************
'****************************************************************
If InStr(xText, srchChar1) <> 0 Then
    blSp = True
    For m = 1 To txLen
        If Mid(xText, m, 1) = srchChar1 Then
            sp = sp + 1
           ' Debug.Print strArray(m)
            'strArray() = strArray(sp, m)
            blSp = True
        End If
    Next m
    Debug.Print blSp
 
    
    xtNo = txLen / lNo 'MAX LINE NO?
    xtNo = CInt(xtNo)
    Debug.Print "xtNo: " & xtNo
    If xtNo > tNo Then 'tNo = max text length variable
        blCutLast = True
    End If
    ReDim strArray(lNo + 1)
    Debug.Print "strArray(lNo): " & strArray(lNo)
    ReDim strLen(sp + 1)
    Debug.Print "strLen(sp+1): " & strLen(sp + 1)
    ReDim posSpace(sp + 1)
End If
'****************************************************************
'***************  Find slash      *******************************
'****************************************************************
If InStr(xText, srchChar1) = 0 And InStr(xText, srchChar2) <> 0 Then
    blSl = True
    For n = 1 To txLen
        If Mid(xText, n, 1) = srchChar2 Then
            sl = sl + 1
            blSl = True
        End If
    Next n
    ReDim strArray(lNo + 1)
    Debug.Print "strArray(lNo): " & strArray(lNo)
    ReDim strLen(sl + 1)
    Debug.Print "strLen(sl+1): " & strLen(sl + 1)
    ReDim posSlash(sl + 1)
    Debug.Print posSlash(0)
End If
'****************************************************************
'***************  End Find  *******************************
'****************************************************************


Debug.Print "Total sp: " & sp & " Total sl: " & sl
'+++++++++++++++++++++++++++++++++++++++++++++++++++++++++++++++++++
'+++++++++++++++++++++++++++++++++++++++++++++++++++++++++++++++++++
'+++++++++++++++++++++++++++++++++++++++++++++++++++++++++++++++++++
If blSp = True Then
    'For i = 1 To sp + 1
    For i = 1 To lNo
        If i = lNo Then
            strArray(i) = Mid(xText, 1, txLen)
            Debug.Print strArray(i)
            xText = ""
            GoTo checkcomb
        Else
            xSp = InStr(xText, srchChar1)
            
            Dim cntSpace As Integer
                For m = 1 To txLen
                    
                        If Mid(xText, m, 1) = srchChar1 Then
                        
                            cntSpace = cntSpace + 1
                            position = m
                            posSpace(cntSpace) = m
                            Debug.Print posSpace(cntSpace)
                            'strArray() = strArray(sp, m)
                            blSp = True
                        End If
                    If m >= tNo Then
                    Exit For
                    End If
                Next m
            If posSpace(cntSpace) = 0 Then
            strArray(i) = Mid(xText, 1, tNo)
            Debug.Print strArray(i)
            xText = Mid(xText, tNo + 1, txLen)
            GoTo skipfor
            End If
            If xSp <> 0 Then 'Whether space exist, if it does then
               'strArray(i) = Mid(xTEXT, 1, xSp)
               strArray(i) = Mid(xText, 1, posSpace(cntSpace))
               Debug.Print strArray(i)
            Else
               strArray(i) = Mid(xText, 1, txLen)
            End If
            
            'strLen(i) = Len(strArray(i)) '+++++++++++++++++++++++++++++Subscription Error
            'xTEXT = Mid(xTEXT, xSp + 1, txLen)
            xText = Mid(xText, posSpace(cntSpace) + 1, txLen)
        End If
skipfor:
    Debug.Print i & ": " & strArray(i)
    Next i
    Debug.Print i & ": " & strArray(i)
End If
'+++++++++++++++++++++++++++++++++++++++++++++++++++++++++++++++++++
'+++++++++++++++++++++++++++++++++++++++++++++++++++++++++++++++++++
'+++++++++++++++++++++++++++++++++++++++++++++++++++++++++++++++++++

If blSp = False And blSl = True Then
    For i = 1 To lNo
        If i = lNo Then
            strArray(i) = Mid(xText, 1, txLen)
            Debug.Print strArray(i)
            xText = ""
            GoTo checkcomb
        Else
            xSl = InStr(xText, srchChar1)
            
            Dim cntSlash As Integer
            For m = 1 To txLen
                
                    If Mid(xText, m, 1) = srchChar2 Then
                    
                        cntSlash = cntSlash + 1
                        position = m
                        posSlash(cntSlash) = m
                        Debug.Print posSlash(cntSlash)
                        'strArray() = strArray(sp, m)
                        blSl = True
                    End If
                If m >= tNo Then
                    Exit For
                End If
            Next m
            If posSlash(cntSlash) = 0 Then
                strArray(i) = Mid(xText, 1, tNo)
                Debug.Print strArray(i)
                xText = Mid(xText, tNo + 1, txLen)
                GoTo skipfor2
            End If
            If xSl <> 0 Then 'Whether space exist, if it does then
               'strArray(i) = Mid(xTEXT, 1, xSp)
               strArray(i) = Mid(xText, 1, posSlash(cntSlash))
               Debug.Print strArray(i)
            Else
               strArray(i) = Mid(xText, 1, txLen)
            End If
            
            strLen(i) = Len(strArray(i))
            'xTEXT = Mid(xTEXT, xSp + 1, txLen)
            xText = Mid(xText, posSlash(cntSlash) + 1, txLen)
            Debug.Print xText
        End If
skipfor2:
    Debug.Print i & ": " & strArray(i)
    Next i
    Debug.Print i & ": " & strArray(i)
End If
'+++++++++++++++++++++++++++++++++++++++++++++++++++++++++++++++++++
'+++++++++++++++++++++++++++++++++++++++++++++++++++++++++++++++++++


'Debug.Print i & ": " & strArray(i)
'****************************CheckComb ***********************
checkcomb:
Debug.Print i & "<<<< i line numbers"
 
'If i - 1 > lNo Then ' combine text
If i > lNo Then  ' combine text
ReDim strArray(k + 1) As String


    For j = 1 To sp + 1
        If j = 1 Then
            xstrArray = ""
            xstrLen = 0
            GoTo NEXTj
        End If
        If xstrLen + strLen(i) > tNo Then
            strArray(i) = xstrArray & strArray(i)
        End If
NEXTj:
        
    Next j
    xstrArray = strArray(i)
        xstrLen = strLen(i)
End If
'**************************** Set Text ***********************

setText:
For k = 1 To lNo
    If k = ATno Then
        'If k = lNo And blCutLast = True Then
        If k = lNo Then
            'SEPTEXT2 = Mid(strArray(k), 1, tNo)
            SEPTEXT2 = strArray(k)
            Exit Function
        End If
    'Debug.Print "strArray(k):" & k & " : " & strArray(k)
    SEPTEXT2 = strArray(k)
    'SEPTEXT2 = "Error"
        If Err.Description = "Subscription error" Then
        MsgBox strArray(i) & " could not be set."
        Exit Function
    End If

    'SEPTEXT2 = "first of range"
    End If
Next k
Erase strArray, strLen, strType 'Jin added this line 10/21/12
Debug.Print SEPTEXT2



End Function

Function SEPTEXT3(xText As String, ATno As Integer, lNo As Integer, tNo As Integer)
Dim strArray() As String
'Dim strData(0) As String
Dim strType() As String
Dim strLen() As Integer
Dim mType, tn As Variant
Dim strTimeStamp, srchChar1, srchChar2, srchChar3, xstrArray As String
Dim pos, txLen, xtNo, xSp, sp, sl, m, n, k, i, j, xstrLen As Integer
Dim blCutLast, blSl, blSp As Boolean

srchChar1 = Chr(32) '32 is space 45 => -, 47 => /
srchChar2 = Chr(45)
srchChar3 = Chr(47)

'strData(0) = xTEXT
pos = 1
sp = 0
sl = 0
If IsNull(xText) = True Then
Exit Function
End If
Debug.Print Len(xText)
txLen = Len(xText)
If txLen = 0 Then
Exit Function
End If


If txLen < tNo Then
    If ATno = 1 Then
    SEPTEXT3 = xText
    Else
    SEPTEXT3 = ""
    End If
    Exit Function
End If

If InStr(xText, srchChar1) <> 0 Then
    blSp = True
    For m = 1 To txLen
        If Mid(xText, m, 1) = srchChar1 Then
            sp = sp + 1
            blSp = True
        End If
    Next m
    ReDim strArray(sp + 1)
    ReDim strLen(sp + 1)
End If


If InStr(xText, srchChar2) <> 0 Then
    blSl = True
    For n = 1 To txLen
        If Mid(xText, n, 1) = srchChar2 Then
            sl = sl + 1
            blSl = True
        End If
    Next n
End If



Debug.Print "Total sp: " & sp & "Total sl: " & sl

xtNo = txLen / lNo 'MAX LINE NO?
xtNo = CInt(xtNo)

If xtNo > tNo Then
    blCutLast = True
End If


If blSp = True Then
    For i = 1 To sp + 1
    If i = lNo Then
    strArray(i) = Mid(xText, 1, txLen)
    xText = ""
    GoTo checkcomb
    Else
        xSp = InStr(xText, srchChar1)
        If xSp <> 0 Then
           strArray(i) = Mid(xText, 1, xSp)
        Else
           strArray(i) = Mid(xText, 1, txLen)
        End If
        
        strLen(i) = Len(strArray(i))
        xText = Mid(xText, xSp + 1, txLen)
    End If
    Debug.Print i & ": " & strArray(i)
    Next i
End If
checkcomb:
Debug.Print i & "<<<< i"
'If i - 1 > lNo Then ' combine text
If i > lNo Then  ' combine text
    For j = 1 To sp + 1
        If j = 1 Then
            xstrArray = ""
            xstrLen = 0
            GoTo NEXTj
        End If
        If xstrLen + strLen(i) > tNo Then
            strArray(i) = xstrArray & strArray(i)
        End If
NEXTj:
        
    Next j
    xstrArray = strArray(i)
        xstrLen = strLen(i)
End If
setText:
For k = 1 To lNo
    If k = ATno Then
        If k = lNo And blCutLast = True Then
            SEPTEXT3 = Mid(strArray(k), 1, tNo)
            Exit Function
        End If
    
    SEPTEXT3 = strArray(k)
    End If
Next k

Debug.Print SEPTEXT3

End Function
'''''''''''''''''''''''''''''''''''''''''''''''''''''''''''''''''''''
'   SEPTEXT2 FROM MOD_SCHED 9/8/14
'
'''''''''''''''''''''''''''''''''''''''''''''''''''''''''''''''''''''
Function SEPTEXT22(xText As String, ATno As Integer, lNo As Integer, tNo As Integer)
Dim strArray() As String
'Dim strData(0) As String
Dim strType() As String
Dim strLen() As Integer
Dim posSpace() As Integer
Dim posDash() As Integer
Dim mType, tn As Variant
Dim strTimeStamp, srchChar1, srchChar2, srchChar3, xstrArray As String
Dim pos, txLen, xtNo, xSp, xDs, sp, sl, ds, m, n, k, i, j, xstrLen, position As Integer
Dim blCutLast, blSl, blSp, blDs As Boolean

srchChar1 = Chr(32) '32 is space 45 => -, 47 => /
srchChar2 = Chr(47)
srchChar3 = Chr(45)

'strData(0) = xTEXT
pos = 1
sp = 0
sl = 0
If IsNull(xText) = True Then
    Exit Function
End If
If xText = "" Then
    Exit Function
End If

Debug.Print Len(xText)
txLen = Len(xText)
If txLen = 0 Then
    Exit Function
End If


If txLen < tNo Then
    If ATno = 1 Then
    'SEPTEXT = ""
        SEPTEXT22 = xText
        Debug.Print "SEPTEXT @ SMALL tNo:" & SEPTEXT22
    Else
        SEPTEXT22 = ""
    End If
    Exit Function
End If
' *************** Find space ***************
If InStr(xText, srchChar1) <> 0 Then
    blSp = True
    For m = 1 To txLen
        If Mid(xText, m, 1) = srchChar1 Then
            sp = sp + 1
           ' Debug.Print strArray(m)
            'strArray() = strArray(sp, m)
            blSp = True
        End If
    Next m
    
    
xtNo = txLen / lNo 'MAX LINE NO?
xtNo = CInt(xtNo)
Debug.Print "xtNo: " & xtNo
If xtNo > tNo Then 'tNo = max text length variable
    blCutLast = True
End If
    
    
    
    ReDim strArray(lNo + 1)
    Debug.Print "strArray(lNo): " & strArray(lNo)
    ReDim strLen(sp + 1)
    Debug.Print "strLen(sp+1): " & strLen(sp + 1)
    ReDim posSpace(sp + 1)
End If

' *************** Find slash ***************

If InStr(xText, srchChar2) <> 0 Then
    blSl = True
    For n = 1 To txLen
        If Mid(xText, n, 1) = srchChar2 Then
            sl = sl + 1
            blSl = True
        End If
    Next n
End If



Debug.Print "Total sp: " & sp & " Total sl: " & sl
' *************** Find DASH ***************
If InStr(xText, srchChar3) <> 0 Then
    blDs = True
    For n = 1 To txLen
        If Mid(xText, n, 1) = srchChar3 Then
            ds = ds + 1
            blDs = True
        End If
    Next n
End If
'**************************************
'**********************************************************************
'**********************************************************************
'************************* blSp ****************************
'**********************************************************************
'**********************************************************************
If blSp = True Then
    For i = 1 To sp + 1
        If i = lNo Then
            strArray(i) = Mid(xText, 1, txLen)
            Debug.Print strArray(i)
            xText = ""
            GoTo checkcomb
        Else
            xSp = InStr(xText, srchChar1)
            Dim cntSpace As Integer
                For m = 1 To txLen
                    
                        If Mid(xText, m, 1) = srchChar1 Then
                        
                            cntSpace = cntSpace + 1
                            position = m
                            posSpace(cntSpace) = m
                            Debug.Print posSpace(cntSpace)
                            'strArray() = strArray(sp, m)
                            blSp = True
                        End If
                    If m >= tNo Then
                    Exit For
                    End If
                Next m
            
            If xSp <> 0 Then
               'strArray(i) = Mid(xTEXT, 1, xSp)
               strArray(i) = Mid(xText, 1, posSpace(cntSpace))
               Debug.Print strArray(i)
            Else
               strArray(i) = Mid(xText, 1, txLen)
            End If
            
            strLen(i) = Len(strArray(i))
            'xTEXT = Mid(xTEXT, xSp + 1, txLen)
            xText = Mid(xText, posSpace(cntSpace) + 1, txLen)
        End If
    Debug.Print i & ": " & strArray(i)
    Next i
End If

'**********************************************************************
'**********************************************************************
'************************* blDs ****************************
'**********************************************************************
'**********************************************************************


If blDs = True Then
    For i = 1 To ds + 1
        If i = lNo Then
            strArray(i) = Mid(xText, 1, txLen)
            Debug.Print strArray(i)
            xText = ""
            GoTo checkcomb
        Else
            xDs = InStr(xText, srchChar3)
            Dim cntDash As Integer
            ReDim posDash(ds)
            
                For m = 1 To txLen
                    
                        If Mid(xText, m, 1) = srchChar3 Then 'If space or dash
                        
                            cntDash = cntDash + 1
                            position = m
                            posDash(cntDash) = m
                            Debug.Print posDash(cntDash)
                            'strArray() = strArray(sp, m)
                            blDs = True
                        End If
                    If m >= tNo Then
                    Exit For
                    End If
                Next m
            
            If xDs <> 0 Then
               'strArray(i) = Mid(xTEXT, 1, xSp)
               strArray(i) = Mid(xText, 1, posDash(cntDash))
               Debug.Print strArray(i)
            Else
               strArray(i) = Mid(xText, 1, txLen)
            End If
            
            strLen(i) = Len(strArray(i))
            'xTEXT = Mid(xTEXT, xSp + 1, txLen)
            xText = Mid(xText, posSpace(cntDash) + 1, txLen)
        End If
    Debug.Print i & ": " & strArray(i)
    Next i
End If

'**********************************************************************
'**********************************************************************
'**********************************************************************
'**********************************************************************

'****************************CheckComb ***********************
checkcomb:
Debug.Print i & "<<<< i"
'If i - 1 > lNo Then ' combine text
If i > lNo Then  ' combine text
ReDim strArray(k + 1) As String


    For j = 1 To sp + 1
        If j = 1 Then
            xstrArray = ""
            xstrLen = 0
            GoTo NEXTj
        End If
        If xstrLen + strLen(i) > tNo Then
            strArray(i) = xstrArray & strArray(i)
        End If
NEXTj:
        
    Next j
    xstrArray = strArray(i)
        xstrLen = strLen(i)
End If
'**************************** Set Text ***********************

setText:
'***************** MOD 3/15/13 *****************'
'If strArray(i) = "" Then
'Exit Function
'End If
'***************** MOD 3/15/13 *****************'
'***************** MOD 2/19/14 *****************'
If SEPTEXT22 = "" Then
Exit Function
End If
If IsNull(SEPTEXT22) = True Then
Exit Function
End If
'***************** E MOD 2/19/14 *****************'
For k = 0 To lNo - 1
    If k = ATno Then
        If k = lNo And blCutLast = True Then
            SEPTEXT22 = Mid(strArray(k), 1, tNo)
            Exit Function
        End If
    
    SEPTEXT22 = strArray(k) 'WAS (K)
    'SEPTEXT2 = "second of range"
    End If
Next k
Erase strArray, strLen, strType 'Jin added this line 10/21/12
Debug.Print SEPTEXT22

End Function

Function SEPTEXT01(xText As String, ATno As Integer, lNo As Integer, tNo As Integer) 'MOD_SCHED
Dim strArray() As String
'Dim strData(0) As String
Dim strType() As String
Dim strLen() As Integer
Dim mType, tn As Variant
Dim strTimeStamp, srchChar1, srchChar2, srchChar3, xstrArray As String
Dim pos, txLen, xtNo, xSp, sp, sl, m, n, k, i, j, xstrLen As Integer
Dim blCutLast, blSl, blSp As Boolean

srchChar1 = Chr(32) '32 is space 45 => -, 47 => /
srchChar2 = Chr(45)
srchChar3 = Chr(47)

'strData(0) = xTEXT
pos = 1
sp = 0
sl = 0
If IsNull(xText) = True Then
    Exit Function
End If
Debug.Print Len(xText)
txLen = Len(xText)
If txLen = 0 Then
    Exit Function
End If


If txLen < tNo Then
    If ATno = 1 Then
    'SEPTEXT = ""
        SEPTEXT01 = xText
        Debug.Print "SEPTEXT01 @ SMALL tNo:" & SEPTEXT01
    Else
        SEPTEXT01 = ""
    End If
    Exit Function
End If
' *************** Find space
If InStr(xText, srchChar1) <> 0 Then
    blSp = True
    For m = 1 To txLen
        If Mid(xText, m, 1) = srchChar1 Then
            sp = sp + 1
            blSp = True
        End If
    Next m
    ReDim strArray(sp + 1)
    Debug.Print "strArray(sp+1): " & strArray(sp + 1)
    ReDim strLen(sp + 1)
    Debug.Print "strLen(sp+1): " & strLen(sp + 1)
End If


If InStr(xText, srchChar2) <> 0 Then
    blSl = True
    For n = 1 To txLen
        If Mid(xText, n, 1) = srchChar2 Then
            sl = sl + 1
            blSl = True
        End If
    Next n
End If



Debug.Print "Total sp: " & sp & "Total sl: " & sl

xtNo = txLen / lNo 'MAX LINE NO?
xtNo = CInt(xtNo)
Debug.Print "xtNo: " & xtNo
If xtNo > tNo Then 'tNo = max text length variable
    blCutLast = True
End If


If blSp = True Then
    For i = 1 To sp + 1
    If i = lNo Then
        strArray(i) = Mid(xText, 1, txLen)
        xText = ""
        GoTo checkcomb
    Else
        xSp = InStr(xText, srchChar1)
        If xSp <> 0 Then
           strArray(i) = Mid(xText, 1, xSp)
        Else
           strArray(i) = Mid(xText, 1, txLen)
        End If
        
        strLen(i) = Len(strArray(i))
        xText = Mid(xText, xSp + 1, txLen)
    End If
    Debug.Print i & ": " & strArray(i)
    Next i
End If
checkcomb:
Debug.Print i & "<<<< i"
'If i - 1 > lNo Then ' combine text
If i > lNo Then  ' combine text
    For j = 1 To sp + 1
        If j = 1 Then
            xstrArray = ""
            xstrLen = 0
            GoTo NEXTj
        End If
        If xstrLen + strLen(i) > tNo Then
            strArray(i) = xstrArray & strArray(i)
        End If
NEXTj:
        
    Next j
    xstrArray = strArray(i)
        xstrLen = strLen(i)
End If
setText:
For k = 1 To lNo
    If k = ATno Then
        If k = lNo And blCutLast = True Then
            SEPTEXT01 = Mid(strArray(k), 1, tNo)
            Exit Function
        End If
    
    SEPTEXT01 = strArray(k)
    End If
Next k
Erase strArray, strLen, strType 'Jin added this line 10/21/12
Debug.Print SEPTEXT01

End Function

Attribute VB_Name = "Test"
Sub testimage()

Dim raster As AcadLayer
Dim image As AcadRasterImage
Dim scalefactor As Double
Dim rotAngle As Double

Dim insertionPoint(0 To 2) As Double

Set raster = ThisDrawing.Layers.Add("Raster")
Application.ActiveDocument.ActiveLayer = raster

'Insert Image into AutoCAD
insertionPoint(0) = 0
insertionPoint(1) = 0
insertionPoint(2) = 0
scalefactor = 40
rotAngle = 0

Set image = Application.ActiveDocument.ModelSpace.AddRaster(PathToRasterImage, _
insertionPoint, scalefactor * 36, rotAngle)
image.Transparency = True
image.scalefactor = scalefactor
image.Name = "New Image"

Application.ActiveDocument.Regen acActiveViewport
Application.ActiveDocument.Save
End Sub
Sub Example_AddRasterExample_AddRaster()
    ' This example adds a raster image in model space.
    
    ' This example uses the "downtown.jpg" found in the sample
    ' directory. If you do not have this image, or it is located
    ' in a different directory, insert a valid path and filename
    ' for the imageName variable below.
    
    Dim insertionPoint(0 To 2) As Double
    Dim scalefactor As Double
    Dim rotationAngle As Double
    Dim imageName As String
    Dim rasterObj As AcadRasterImage
    imageName = "C:/violin01.jpg"
    insertionPoint(0) = 5#: insertionPoint(1) = 5#: insertionPoint(2) = 0#
    scalefactor = 1#
    rotationAngle = 0
    
    On Error Resume Next
    ' Creates a raster image in model space
    Set rasterObj = ThisDrawing.ModelSpace.AddRaster(imageName, insertionPoint, scalefactor, rotationAngle)
    Debug.Print imageName
    If Err.Description = "File error" Then
        MsgBox imageName & " could not be found."
        Exit Sub
    End If
End Sub

Attribute VB_Name = "TxtStyle"
Sub CreateCNstyle()
Dim newText As AcadTextStyle
Dim blnFoundText As Boolean
Dim blnFoundTitle As Boolean
Dim blnFoundSub As Boolean
   
'reset blnFound
blnFoundText = False
blnFoundTitle = False
blnFoundSub = False

    For i = 0 To ThisDrawing.TextStyles.Count - 1  'make the styles for the form
        Debug.Print ThisDrawing.TextStyles(i).Name
        If ThisDrawing.TextStyles(i).Name = "CN" Then
            blnFoundText = True
            Exit Sub
        End If
        
    Next i

Set newText = ThisDrawing.TextStyles.Add("CN")

typeface = "Courier new"
newText.SetFont typeface, Bold, Italic, Charset, PitchandFamily

End Sub
Sub CreateARstyle()
Dim newText As AcadTextStyle
Dim blnFoundText As Boolean
Dim blnFoundTitle As Boolean
Dim blnFoundSub As Boolean
   
'reset blnFound
blnFoundText = False
blnFoundTitle = False
blnFoundSub = False

    For i = 0 To ThisDrawing.TextStyles.Count - 1  'make the styles for the form
        Debug.Print ThisDrawing.TextStyles(i).Name
        If ThisDrawing.TextStyles(i).Name = "AR" Then
            blnFoundText = True
            Exit Sub
        End If
        
    Next i

Set newText = ThisDrawing.TextStyles.Add("AR")
typeface = "arial"

newText.SetFont typeface, Bold, Italic, Charset, PitchandFamily

End Sub

Sub CreateRstyle()
Dim newText As AcadTextStyle
Dim blnFoundText As Boolean
Dim blnFoundTitle As Boolean
Dim blnFoundSub As Boolean
   
'reset blnFound
blnFoundText = False
blnFoundTitle = False
blnFoundSub = False

    For i = 0 To ThisDrawing.TextStyles.Count - 1  'make the styles for the form
        Debug.Print ThisDrawing.TextStyles(i).Name
        If ThisDrawing.TextStyles(i).Name = "R" Then
            blnFoundText = True
            Exit Sub
        End If
        
    Next i

Set newText = ThisDrawing.TextStyles.Add("R")
typeface = "romans"

newText.SetFont typeface, Bold, Italic, Charset, PitchandFamily

End Sub
Sub CreateRstyle1() 'FROM MOD_SCHED
Dim newText As AcadTextStyle
Dim blnFoundText As Boolean
Dim blnFoundTitle As Boolean
Dim blnFoundSub As Boolean
   
'reset blnFound
blnFoundText = False
blnFoundTitle = False
blnFoundSub = False

    For i = 0 To ThisDrawing.TextStyles.Count - 1  'make the styles for the form
        Debug.Print ThisDrawing.TextStyles(i).Name
        If ThisDrawing.TextStyles(i).Name = "R" Then
            blnFoundText = True
            Exit Sub
        End If
        
    Next i

Set newText = ThisDrawing.TextStyles.Add("R")
typeface = "romans"

newText.SetFont typeface, Bold, Italic, Charset, PitchandFamily

End Sub

Sub CreateARstyle1() 'MOD_SPEC
Dim newText As AcadTextStyle
Dim blnFoundText As Boolean
Dim blnFoundTitle As Boolean
Dim blnFoundSub As Boolean
   
'reset blnFound
blnFoundText = False
blnFoundTitle = False
blnFoundSub = False

    For i = 0 To ThisDrawing.TextStyles.Count - 1  'make the styles for the form
        Debug.Print ThisDrawing.TextStyles(i).Name
        If ThisDrawing.TextStyles(i).Name = "AR" Then
            blnFoundText = True
            Exit Sub
        End If
        
    Next i

Set newText = ThisDrawing.TextStyles.Add("AR")
typeface = "arial"

newText.SetFont typeface, Bold, Italic, Charset, PitchandFamily

End Sub

Attribute VB_Name = "WorkItem"
Public Sub ShowWorkItem()
frmWorkItem.show
End Sub
Public Sub writeAssWorkItemImg()


Dim DB As Database
Dim rstProjDiv, rstProjAss, rstAssWorkItem, rstWorkImg As Recordset
Dim strProjDiv, strProjAss, strAssWorkItem, strWorkImg, txtRow As String
Dim rnProjDiv, rnProjAss, rnAssWorkItem, rnWorkImg As Integer     'ProjSet no.
'Dim rcArray As Variant
Dim TblPT(0 To 2) As Double
Dim tblPT2(0 To 2) As Double
Dim tmpArrayAss(0 To 1) As Double

Dim tblWidth As Double
Dim txtHt As Double
Dim textObj As AcadText
Dim attributeObj As AcadAttribute
Dim height As Double
Dim mode As Long
Dim prompt As String

'**********IMG********************
Dim nHeadDwg, nDivDwg, nWkCsiDwg, nRowDwg, nFootDwg, nImgDwg As Variant
Dim nJumpHead, nJumpGroup, nJumpRow As Integer
'**********IMG********************
Dim blockRefObj As AcadBlockReference
Dim BlkObj As Object
Dim xDivNo, xAssID, i, iDiv, irnDiv, irnAss, j, k, irnWorkItem, iattr_DIV, iattr_ASS, iattr_WORKITEM As Integer
Dim mg, iattr_Img As Integer

'frmWorkItem.ListBox1.Clear
CreateCNstyle
TblPT(0) = 0: TblPT(1) = 0: TblPT(2) = 0
tblPT2(0) = -300: tblPT2(1) = 0: tblPT2(2) = 0
txtHt = 4
txtRow = ""
mode = acAttributeModeVerify

''InsertJBlock "e:\drawfile\jvba\XHDWRHEAD01.dwg", tblPT, "Model"
'ThisDrawing.ModelSpace.InsertBlock tblPT, "e:\drawfile\jvba\XHDWRHEAD02.dwg", 1, 1, 1, 0
'InsertJBlock "e:\drawfile\jvba\XHDWRGPROW02.dwg", tblPT2, "Model"
'InsertJBlock "e:\drawfile\jvba\XHDWRROW02.dwg", tblPT2, "Model"
'InsertJBlock "e:\drawfile\jvba\XHDWRFOOT02.dwg", tblPT2, "Model"

'ThisDrawing.SelectionSets.Item("XHDWRGPROW01").Delete
'ThisDrawing.SelectionSets.Item("XHDWRROW01").Delete

If frmWorkItem.ShowImage = True Then
    nHeadDwg = "\\jwja-svr-10\drawfile\jvba\X_WORKITEM_HEAD01.dwg"
    'nGroupDwg = "H:\drawfile\jvba\XHDWRGPROW03.dwg"
    nDivDwg = "\\jwja-svr-10\drawfile\jvba\X_WORKITEM_DIV_ROW01.dwg"
    nWkCsiDwg = "\\jwja-svr-10\drawfile\jvba\X_WORKITEM_WKCSI_ROW01.dwg"
    nRowDwg = "\\jwja-svr-10\drawfile\jvba\X_WORKITEM_ROW01.dwg"
    nImgFillDwg = "\\jwja-svr-10\drawfile\jvba\X_WORKITEM_ImgFill01.dwg"
    nFootDwg = "\\jwja-svr-10\drawfile\jvba\X_WORKITEM_FOOT01.dwg"
    nJumpHead = 60 'was 24
    nJumpDiv = 20 'was 66
    nJumpWkCSI = 20
    nJumpRow = 72 'was 60
    InsertJBlock "\\jwja-svr-10\drawfile\jvba\X_WORKITEM_HEAD10.dwg", TblPT, "Model"
Else
    'nHeadDwg = "H:\drawfile\jvba\X_WORKITEM_HEAD02.dwg"
    nHeadDwg = "\\jwja-svr-10\drawfile\jvba\X_WORKITEM_HEAD10.dwg"
    'nGroupDwg = "H:\drawfile\jvba\XHDWRGPROW03.dwg"
    nDivDwg = "\\jwja-svr-10\drawfile\jvba\X_WORKITEM_DIV_ROW02.dwg"
    nWkCsiDwg = "\\jwja-svr-10\drawfile\jvba\X_WORKITEM_WKCSI_ROW01.dwg"
    'nRowDwg = "H:\drawfile\jvba\X_WORKITEM_ROW02.dwg"
    nRowDwg = "\\jwja-svr-10\drawfile\jvba\X_WORKITEM_ROW10.dwg"
    'nImgFillDwg = "H:\drawfile\jvba\X_WORKITEM_ImgFill03.dwg" 'Why is this 03?
    nImgFillDwg = "\\jwja-svr-10\drawfile\jvba\X_WORKITEM_ImgFill01.dwg"
    nFootDwg = "\\jwja-svr-10\drawfile\jvba\X_WORKITEM_FOOT01.dwg"
    nJumpHead = 60 'was 24
    nJumpDiv = 20 'was 66
    nJumpWkCSI = 20
    nJumpRow = 72 'was 60
    'InsertJBlock "H:\drawfile\jvba\X_WORKITEM_HEAD02.dwg", tblPT, "Model"
    InsertJBlock "\\jwja-svr-10\drawfile\jvba\X_WORKITEM_HEAD10.dwg", TblPT, "Model"
End If

TblPT(1) = TblPT(1) - nJumpHead

'Set DB = OpenDatabase("H:\db\db_est\H_H_EST_2013_001.mdb")
Set DB = OpenDatabase("\\jwja-svr-10\jdb\db_est\x_EST_2013_001.mdb")

Dim varItm As Variant


With frmWorkItem.ListBox1
For il = 0 To .ListCount - 1
If .Selected(il) Then




    'xAssDiv = !assdiv
    'xAssID = ListBox1.List(il, 0)
'    Debug.Print .Column(il, 0)
    Debug.Print .Column(0, il)
    xAssID = .Column(0, il)
    Debug.Print xAssID
    'strProjAss = "SELECT ASS.ASSID, ASS.ESTID, ASS.ASSDIV, ASS.ASSNO, ASS.ASSSUBDIV, ass.csi, ASS.ASSNAME, ASS.proj_no " _
    & "FROM ASS " _
    & "WHERE (((ASS.proj_no) = '" & frmWorkItem.seleproj & "'))" _
    & "ORDER BY ASS.ASSDIV, ASS.ASSNO"
    'strProjAss = "SELECT ASS.ASSID, ASS.ESTID, ASS.ASSDIV, ASS.ASSNO, ASS.ASSSUBDIV, ASS.CSI, ASS.ASSNAME, ASS.proj_no " _
    & "FROM ASS " _
    & "WHERE (((ASS.ASSID) =" & xAssID & "))" _
    & "ORDER BY ASS.CSI;"
If frmWorkItem.mCategory = True Then
    strProjAss = "SELECT ASS.ASSID, ASS.ESTID, ASS.ASSDIV, ASS.ASSSUBDIV, ASS.ASSNO, ASS.ASSNAME, ASS.ASSNOTE, ASS.ASSDATE, " _
    & "ASS.proj_no, ASS.WKID, ASS.CSID, ASS.CSI, ASS.ASSAMT, ASS.BUAMT, ASS.MASSAMT, " _
    & "ASS.CATEGORY_ID, CATEGORY.category_no, CATEGORY.category, CATEGORY.category_note " _
    & "FROM ASS INNER JOIN CATEGORY ON ASS.CATEGORY_ID=CATEGORY.category_id " _
    & "WHERE (((ASS.ASSID) =" & xAssID & "))" _
    & "ORDER BY CATEGORY.category_no;"
Else
    strProjAss = "SELECT ASS.ASSID, ASS.ESTID, ASS.ASSDIV, ASS.ASSSUBDIV, ASS.ASSNO, ASS.ASSNAME, ASS.ASSNOTE, ASS.ASSDATE, " _
    & "ASS.proj_no, ASS.WKID, ASS.CSID, ASS.CSI, ASS.ASSAMT, ASS.BUAMT, ASS.MASSAMT, " _
    & "ASS.CATEGORY_ID, CATEGORY.category_no, CATEGORY.category, CATEGORY.category_note " _
    & "FROM ASS INNER JOIN CATEGORY ON ASS.CATEGORY_ID=CATEGORY.category_id " _
    & "WHERE (((ASS.ASSID) =" & xAssID & "))" _
    & "ORDER BY ASS.CSI;"
End If
    
    Set rstProjAss = DB.OpenRecordset(strProjAss)
    Debug.Print rstProjAss.RecordCount
        If rstProjAss.RecordCount = 0 Then
            'GoTo Exit_writeAssWorkItemImg
        End If
    Debug.Print rstProjAss.RecordCount
    rstProjAss.MoveLast
    rstProjAss.MoveFirst
    Debug.Print rstProjAss.RecordCount
    Debug.Print rnProjAss
    rnProjAss = rstProjAss.RecordCount
        
        With rstProjAss
            Debug.Print !ASSID & "<<<<assid"
            Debug.Print !csi & "<<<<CSI"
            Debug.Print !ASSNAME & "<<<<ASSNAME"
            'xAssID = !assid
            'Debug.Print xAssID
            For j = 1 To rnProjAss
                xAssID = !ASSID
                Debug.Print xAssID
                Set blockRefObj = ThisDrawing.ModelSpace.InsertBlock _
                             (TblPT, nWkCsiDwg, 1, 1, 1, 0)
                Dim varAttributes2 As Variant
                varAttributes2 = blockRefObj.GetAttributes
                For iattr_ASS = LBound(varAttributes2) To UBound(varAttributes2)
                    Debug.Print varAttributes2(iattr_ASS).TagString
                    If varAttributes2(iattr_ASS).TagString = "XASSCSI" Then
                        If IsNull(!csi) = True Then
                            varAttributes2(iattr_ASS).textString = ""
                        Else
                        '******** Edited 8/14/16************
                            If frmWorkItem.mCategory = True Then
                            varAttributes2(iattr_ASS).textString = !category_no
                            Debug.Print !category_no
                            Else
                            varAttributes2(iattr_ASS).textString = !csi
                            End If
                        '***********************************
                            Debug.Print varAttributes2(iattr_ASS).textString
                        End If
                    End If
                    If varAttributes2(iattr_ASS).TagString = "XASSNAME" Then
                        Debug.Print !ASSNAME & "<<<< ASSNAME"
                        If IsNull(!ASSNAME) = True Then
                            varAttributes2(iattr_ASS).textString = ""
                        Else
                            '=DLookUp("csiname","csi","left(csi,2) = " & CStr([assdiv]))
                        '******** Edited 8/14/16************
                            If frmWorkItem.mCategory = True Then
                            varAttributes2(iattr_ASS).textString = !category
                            Else
                            varAttributes2(iattr_ASS).textString = !ASSNAME
                            End If
                        '***********************************
                            Debug.Print varAttributes2(iattr_ASS).textString
                        End If
                    End If
                Next iattr_ASS
                TblPT(1) = TblPT(1) - nJumpWkCSI
                tempYpos = TblPT(1)
                strAssWorkItem = "SELECT WORK.ASSID, WORK.WKID, WORK.WKCSINO, WORK.WKCSINAME, WORK.WKNOTE ,WORK.WKNOTE_EX " _
                & "FROM ASS INNER JOIN [WORK] ON ASS.ASSID = WORK.ASSID " _
                & "WHERE (((WORK.ASSID) =" & xAssID & "))" _
                & "ORDER BY WORK.WKCSINO;"
                'Debug.Print xwkID
                Set rstAssWorkItem = DB.OpenRecordset(strAssWorkItem)
                Debug.Print rstAssWorkItem.RecordCount
                'Debug.Print strHDSet
                If rstAssWorkItem.RecordCount = 0 Then
                    GoTo Exit_writeAssWorkItemImg
                End If
                rstAssWorkItem.MoveLast
                rstAssWorkItem.MoveFirst
                Debug.Print rstAssWorkItem.RecordCount
                Debug.Print rnAssWorkItem
                rnAssWorkItem = rstAssWorkItem.RecordCount
                With rstAssWorkItem
                    'xwkid = !wkid
                    Debug.Print xwkid
                    For k = 1 To rnAssWorkItem
                        xwkid = !wkid
                        Set blockRefObj = ThisDrawing.ModelSpace.InsertBlock _
                                     (TblPT, nRowDwg, 1, 1, 1, 0)
    '**************************************************************************************
                        Dim imgPT(0 To 2) As Double
                        Dim fillPT(0 To 2) As Double
                        Dim scalefactor, xSF As Double
                        Dim rotAngleInDegree As Double, rotAngle As Double
                        'Dim imageName As String
                        Dim imageName As String
                        Dim raster As AcadRasterImage
                        Dim imgheight As Variant
                        Dim imgwidth As Variant
                        Dim width As Double
                        Dim corner(0 To 2) As Double
                        Dim corner2(0 To 2) As Double
                        strWorkImg = "SELECT work.wkid, connwkpic.picid, PROJ_PIC.PICFULLNAME, PROJ_PIC.PICFULLNAMESM " _
                                & "FROM [WORK] INNER JOIN (connwkpic INNER JOIN PROJ_PIC ON connwkpic.picid = PROJ_PIC.PICID) " _
                                & "ON WORK.WKID = connwkpic.workid " _
                                & "WHERE (((work.wkid)=" & xwkid & "));"
    
                        Set rstWorkImg = DB.OpenRecordset(strWorkImg)
                        rnWorkImg = rstWorkImg.RecordCount
                        'Do While Not rstWorkImg.EOF
                            Debug.Print rstWorkImg.RecordCount
                            If rstWorkImg.RecordCount = 0 Then
                                GoTo SkipImg
                            Else
                                rstWorkImg.MoveLast
                                rstWorkImg.MoveFirst
                            End If
                            Debug.Print rstWorkImg.RecordCount
                            Debug.Print rnWorkImg
                            rnWorkImg = rstWorkImg.RecordCount
                            nImgFill = Round(rnWorkImg / 2, 0)
                            Debug.Print nImgFill & "<<<<<< nImgFill >>>>"
                                imgPT(0) = TblPT(0) + 6
                                imgPT(1) = TblPT(1) - 68
                                imgPT(2) = TblPT(2)
        
                            With rstWorkImg 'img1
                                rstWorkImg.MoveLast
                                rstWorkImg.MoveFirst
                                'If rstWorkImg.RecordCount = 0 Then
                                   ' Exit For
                                'End
                                For mg = 1 To rnWorkImg
                                    'If !PICFULLNAME <> "" Then
                                    If mg = 2 Then
                                        imgPT(0) = TblPT(0) + 66
                                    End If
                                    If frmWorkItem.ShowImage = True Then
                                
                                    'imageName = "C:\AutoCAD\sample\downtown.jpg"
                                    If IsNull(!picfullname) = False Then
                                        If IsNull(!picfullnamesm) = False Then
                                        imageName = !picfullnamesm
                                        Else
                                        imageName = !picfullname
                                        End If
                                    Else
                                        imageName = ""
                                    End If
                                    Debug.Print mg & ": " & imageName
                                    corner(0) = imgPT(0) + 12
                                    corner(1) = imgPT(1) - 1
                                    corner(2) = imgPT(2)
                                    width = 48 '4' X 12
                                    Set mtextObj = ThisDrawing.ModelSpace.AddMText(corner, width, !picid)
                                        'MTextObj.StyleName = "R"
                                        'MTextObj.Layer = "DI48"
                                        mtextObj.Color = acRed
                                        mtextObj.height = 2
                                        mtextObj.Update
                                        corner2(0) = imgPT(0) + 12
                                        corner2(1) = imgPT(1) + 12
                                        corner2(2) = imgPT(2)
                                    Set mtextObj = ThisDrawing.ModelSpace.AddMText(corner2, width, mg)
                                        'CreateARstyle
                                        'MTextObj.StyleName = "R"
                                        'MTextObj.Layer = "DEFPOINTS"
                                        mtextObj.height = 2
                                        mtextObj.Update
                                        'Debug.Print imageName
                                        'insertionPoint(0) = 2#: insertionPoint(1) = 2#: insertionPoint(2) = 0#
                                        scalefactor = 48#
                                        'rotAngleInDegree = 0#
                                        'rotAngle = rotAngleInDegree * 3.141592 / 180#
                                        rotAngle = 0#
                                        ' Creates a raster image in model space
                                        'If !fximgname <> "" Then
                                        Debug.Print imageName
                                        Debug.Print imgPT(0) & ":" & imgPT(1) & ":" & imgPT(2)
                                        Debug.Print scalefactor
                                        Debug.Print rotAngle
                                        
                                    Set raster = ThisDrawing.ModelSpace.AddRaster(imageName, imgPT, scalefactor, rotAngle)
                                    If Err.Description = "File error" Then
                                        MsgBox imageName & " could not be found."
                                        Exit Sub
                                    End If
                                        With raster
                                            imgheight = raster.ImageHeight
                                            imgwidth = raster.ImageWidth
                                                If imgheight > 48 Then
                                                    xSF = (48 / imgheight) * 48
                                                    Debug.Print "xSF: " & xSF * 48
                                                     raster.scalefactor = xSF
                                                End If
                                        End With
                                     End If
                                    'End If
                                    'imgPT(1) = imgPT(1) - nJumpRow
                                    If ((mg Mod 2) = 0) Then 'even
                                        Debug.Print mg Mod 2 & "see mod"
                                        imgPT(0) = TblPT(0) + 66
                                        imgPT(1) = imgPT(1) - 56
                                    Else
                                        imgPT(0) = TblPT(0) + 6
                                        'imgPT(1) = imgPT(1) - 54
                                    End If
                                    Debug.Print "mg:>>>> " & mg & " of Total: " & rnWorkImg & "Image: " & imageName
                                    .MoveNext
                                Next mg
                                '.MoveNext
                            End With 'img1
                            '.MoveNext
                        'Loop
    '**************************************************************************************
                        Dim CsiPos(0 To 2) As Double
                        CsiPos(0) = TblPT(0) - 360
                        CsiPos(1) = TblPT(1)
                        CsiPos(2) = TblPT(2)
                        width = 240 '4' X 12
                        CSILabel = UCase(!wkcsino & "-" & !WKCSINAME)
                        CreateRstyle
                        Set mtextObj = ThisDrawing.ModelSpace.AddMText(CsiPos, width, CSILabel)
                            mtextObj.StyleName = "R"
                            mtextObj.height = 4
                            mtextObj.Layer = "DI48"
                            mtextObj.Update
                        CsiPos(0) = CsiPos(0) - 240
                        width = 84 '4' X 12
                        Set mtextObj = ThisDrawing.ModelSpace.AddMText(CsiPos, width, !wkcsino)
                            mtextObj.StyleName = "R"
                            mtextObj.height = 4
                            mtextObj.Layer = "DI48"
                            mtextObj.Update
    '**************************************************************************************
SkipImg:
                        Dim varAttributes3 As Variant
                        varAttributes3 = blockRefObj.GetAttributes
    
                        For iattr_WKCSI = LBound(varAttributes3) To UBound(varAttributes3)
                            Debug.Print varAttributes3(iattr_WKCSI).TagString
                            If varAttributes3(iattr_WKCSI).TagString = "XWKCSINO" Then
                                If IsNull(!wkcsino) = True Then
                                    varAttributes3(iattr_WKCSI).textString = ""
                                Else
                                    varAttributes3(iattr_WKCSI).textString = !wkcsino
                                End If
                            End If
                            If varAttributes3(iattr_WKCSI).TagString = "XWKCSINAME" Then
                                If IsNull(!WKCSINAME) = True Then
                                    varAttributes3(iattr_WKCSI).textString = ""
                                Else
                                    varAttributes3(iattr_WKCSI).textString = !WKCSINAME
                                End If
                            End If
                            If varAttributes3(iattr_WKCSI).TagString = "XNOTE1" Then
                                If IsNull(!WKNOTE_EX) = True Then
                                    varAttributes3(iattr_WKCSI).textString = ""
                                Else
                                    varAttributes3(iattr_WKCSI).textString = SEPTEXT2(!WKNOTE_EX, 1, 5, 22)
                                End If
                            End If
                            If varAttributes3(iattr_WKCSI).TagString = "XNOTE2" Then
                                If IsNull(!WKNOTE_EX) = True Then
                                    varAttributes3(iattr_WKCSI).textString = ""
                                Else
                                    varAttributes3(iattr_WKCSI).textString = SEPTEXT2(!WKNOTE_EX, 2, 5, 22)
                                End If
                            End If
                            If varAttributes3(iattr_WKCSI).TagString = "XNOTE2" Then
                                If IsNull(!WKNOTE_EX) = True Then
                                    varAttributes3(iattr_WKCSI).textString = ""
                                Else
                                    varAttributes3(iattr_WKCSI).textString = SEPTEXT2(!WKNOTE_EX, 3, 5, 22)
                                End If
                            End If
                                     If varAttributes3(iattr_WKCSI).TagString = "XNOTE3" Then
                                If IsNull(!WKNOTE_EX) = True Then
                                    varAttributes3(iattr_WKCSI).textString = ""
                                Else
                                    varAttributes3(iattr_WKCSI).textString = SEPTEXT2(!WKNOTE_EX, 4, 5, 22)
                                End If
                            End If
                              If varAttributes3(iattr_WKCSI).TagString = "XNOTE4" Then
                                If IsNull(!WKNOTE_EX) = True Then
                                    varAttributes3(iattr_WKCSI).textString = ""
                                Else
                                    varAttributes3(iattr_WKCSI).textString = SEPTEXT2(!WKNOTE_EX, 5, 5, 22)
                                End If
                            End If
                              If varAttributes3(iattr_WKCSI).TagString = "XNOTE5" Then
                                If IsNull(!WKNOTE_EX) = True Then
                                    varAttributes3(iattr_WKCSI).textString = ""
                                Else
                                    varAttributes3(iattr_WKCSI).textString = SEPTEXT2(!WKNOTE_EX, 5, 5, 22)
                                End If
                            End If
                            If varAttributes3(iattr_WKCSI).TagString = "XNWNOTE1" Then
                                If IsNull(!WKNOTE) = True Then
                                    varAttributes3(iattr_WKCSI).textString = ""
                                Else
                                    varAttributes3(iattr_WKCSI).textString = SEPTEXT2(!WKNOTE, 1, 5, 22)
                                End If
                            End If
                            If varAttributes3(iattr_WKCSI).TagString = "XNWNOTE2" Then
                                If IsNull(!WKNOTE) = True Then
                                    varAttributes3(iattr_WKCSI).textString = ""
                                Else
                                    varAttributes3(iattr_WKCSI).textString = SEPTEXT2(!WKNOTE, 2, 5, 22)
                                End If
                            End If
                            If varAttributes3(iattr_WKCSI).TagString = "XNWNOTE3" Then
                                If IsNull(!WKNOTE) = True Then
                                    varAttributes3(iattr_WKCSI).textString = ""
                                Else
                                    varAttributes3(iattr_WKCSI).textString = SEPTEXT2(!WKNOTE, 3, 5, 22)
                                End If
                            End If
                            If varAttributes3(iattr_WKCSI).TagString = "XNWNOTE4" Then
                                If IsNull(!WKNOTE) = True Then
                                    varAttributes3(iattr_WKCSI).textString = ""
                                Else
                                    varAttributes3(iattr_WKCSI).textString = SEPTEXT2(!WKNOTE, 4, 5, 22)
                                End If
                            End If
                            If varAttributes3(iattr_WKCSI).TagString = "XNWNOTE5" Then
                                If IsNull(!WKNOTE) = True Then
                                    varAttributes3(iattr_WKCSI).textString = ""
                                Else
                                    varAttributes3(iattr_WKCSI).textString = SEPTEXT2(!WKNOTE, 5, 5, 22)
                                End If
                            End If
    '**************************************************************************************
                            If varAttributes3(iattr_WKCSI).TagString = "XBY1" Then
                                Debug.Print WRITEWORKBY(!wkid)
                                If IsNull(WRITEWORKBY(!wkid)) = True Then
                                    varAttributes3(iattr_WKCSI).textString = ""
                                Else
                                    varAttributes3(iattr_WKCSI).textString = SEPTEXT2(WRITEWORKBY(!wkid), 1, 2, 22)
                                End If
                            End If
                            If varAttributes3(iattr_WKCSI).TagString = "XBY2" Then
                                If IsNull(WRITEWORKBY(!wkid)) = True Then
                                    varAttributes3(iattr_WKCSI).textString = ""
                                Else
                                    varAttributes3(iattr_WKCSI).textString = SEPTEXT2(WRITEWORKBY(!wkid), 2, 2, 22)
                                End If
                            End If
                            If varAttributes3(iattr_WKCSI).TagString = "XACT1" Then
                                If IsNull(printAction(!wkid)) = True Then
                                    varAttributes3(iattr_WKCSI).textString = ""
                                Else
                                    varAttributes3(iattr_WKCSI).textString = SEPTEXT2(printAction(!wkid), 1, 2, 22)
                                End If
                            End If
                            If varAttributes3(iattr_WKCSI).TagString = "XACT2" Then
                                If IsNull(printAction(!wkid)) = True Then
                                    varAttributes3(iattr_WKCSI).textString = ""
                                Else
                                    varAttributes3(iattr_WKCSI).textString = SEPTEXT2(printAction(!wkid), 2, 2, 22)
                                End If
                            End If

    '**************************************************************************************
                        Next iattr_WKCSI
                        
    '******* FILL DWG ************** GOT IT TO WORK ON 11/11/12 *****************************
                        nImgFill = Round(rnWorkImg / 2, 0)
                        Debug.Print "k>>>>>>>>>>>>>>: " & k
                        Debug.Print TblPT(0) & " : " & TblPT(1) & " : " & TblPT(2) & "<<<<<<< tblPT"
                        fillPT(0) = TblPT(0)
                        fillPT(1) = TblPT(1) - nJumpRow
                        fillPT(2) = TblPT(2)
                        Debug.Print fillPT(0) & " : " & fillPT(1) & " : " & fillPT(2) & "<<<<<< fillPT"
                        Debug.Print tempYpos
                        If nImgFill >= 2 Then
                            For iFill = 1 To nImgFill - 1
                                Set blockRefObj = ThisDrawing.ModelSpace.InsertBlock _
                                                    (fillPT, nImgFillDwg, 1, 1, 1, 0)
                                fillPT(1) = fillPT(1) - 56
                            Next iFill
                        End If
                            If nImgFill < 2 Then
                                TblPT(1) = TblPT(1) - nJumpRow
                            Else
                                TblPT(1) = TblPT(1) - nJumpRow - ((nImgFill - 1) * 56)
                            End If
     '***** FILL DWG *************************************************************************
                        .MoveNext
                    Next k 'rnAssWorkItem
                    '.MoveNext
                End With
                'rstWorkItem.Close
                .MoveNext
            Next j 'rnProjAss
            
    End With 'rstProjAss first with
End If
Next il
End With
'rstProjAss.Close
Set blockRefObj = ThisDrawing.ModelSpace.InsertBlock _
                                             (TblPT, nFootDwg, 1, 1, 1, 0)
''ThisDrawing.SelectionSets.Item("hdwrsched").Delete
'rstProjDiv.Close
'rstProjAss.Close
'rstWorkItem.Close


'RsHDwrSet.Close
Set DB = Nothing

''Else

''ThisDrawing.SelectionSets.Item("hdwrsched").Delete
'no attribute block, inform the user
'

'MsgBox "Inserted block! Re-run this program.", vbCritical, "JWJA"

'delete the selection set
'ThisDrawing.SelectionSets.Item("TBLK").Delete

''End If

'Set MTextObj = ThisDrawing.ModelSpace.AddMText(corner, width, text)

''ThisDrawing.SelectionSets.Item("hdwrsched").Delete


Exit_writeAssWorkItemImg:
frmWorkItem.Hide

End Sub
Public Sub writeAssWorkItemImgCAD()
'+++++++++++++++++++++++++++++++++++++++++++++++++++++++++
'+++++++++++++++++++++++++++++++++++++++++++++++++++++++++
'+          11/14/12 FOR CAD USE WITH NO OF IMAGE CONTROL
'+          03/18/14 FOR LARGE PICTURE
'+
'+++++++++++++++++++++++++++++++++++++++++++++++++++++++++
'+++++++++++++++++++++++++++++++++++++++++++++++++++++++++

Dim DB As Database
Dim rstProjDiv, rstProjAss, rstAssWorkItem, rstWorkImg As Recordset
Dim strProjDiv, strProjAss, strAssWorkItem, strWorkImg, txtRow As String
Dim rnProjDiv, rnProjAss, rnAssWorkItem, rnWorkImg As Integer     'ProjSet no.
'Dim rcArray As Variant
Dim TblPT(0 To 2) As Double
Dim tblPT2(0 To 2) As Double
Dim tmpArrayAss(0 To 1) As Double

Dim tblWidth As Double
Dim txtHt As Double
Dim textObj As AcadText
Dim attributeObj As AcadAttribute
Dim height As Double
Dim mode As Long
Dim prompt As String

'**********IMG********************
Dim nHeadDwg, nDivDwg, nWkCsiDwg, nRowDwg, nFootDwg, nImgDwg As Variant
Dim nJumpHead, nJumpGroup, nJumpRow As Integer
'**********IMG********************
Dim blockRefObj As AcadBlockReference
Dim BlkObj As Object
Dim xDivNo, xAssID, i, iDiv, irnDiv, irnAss, j, k, irnWorkItem, iattr_DIV, iattr_ASS, iattr_WORKITEM As Integer
Dim mg, iattr_Img As Integer

'frmWorkItem.ListBox1.Clear
'CreateCNstyle
TblPT(0) = 0: TblPT(1) = 0: TblPT(2) = 0
tblPT2(0) = -300: tblPT2(1) = 0: tblPT2(2) = 0
txtHt = 4
txtRow = ""
mode = acAttributeModeVerify


If frmWorkItem.ShowImage = True Then
    If frmWorkItem.PrintLarge = True Then
        nHeadDwg = "\\jwja-svr-10\drawfile\jvba\XCSI_HD_10.dwg"
        'nGroupDwg = "H:\drawfile\jvba\XHDWRGPROW03.dwg"
        nDivDwg = "\\jwja-svr-10\drawfile\jvba\XCSI_DIV_01.dwg"
        nWkCsiDwg = "\\jwja-svr-10\drawfile\jvba\XCSI_ASS_01.dwg"
        nRowDwg = "\\jwja-svr-10\drawfile\jvba\XCSI_WORK_ROW_10.dwg"
        'nImgFillDwg = "H:\drawfile\jvba\X_WORKITEM_ImgFill01.dwg"
        nFootDwg = "\\jwja-svr-10\drawfile\jvba\XCSI_FOOT_01.dwg"
        nJumpHead = 42 'was 60
        nJumpDiv = 18 'was 20
        nJumpWkCSI = 18 'WAS 20
        nJumpRow = 132 'was 72
        InsertJBlock "\\jwja-svr-10\drawfile\jvba\XCSI_HD_10.dwg", TblPT, "Model"

    Else
        nHeadDwg = "\\jwja-svr-10\drawfile\jvba\XCSI_HD_01.dwg"
        'nGroupDwg = "H:\drawfile\jvba\XHDWRGPROW03.dwg"
        nDivDwg = "\\jwja-svr-10\drawfile\jvba\XCSI_DIV_01.dwg"
        nWkCsiDwg = "\\jwja-svr-10\drawfile\jvba\XCSI_ASS_01.dwg"
        nRowDwg = "\\jwja-svr-10\drawfile\jvba\XCSI_WORK_ROW_01.dwg"
        'nImgFillDwg = "H:\drawfile\jvba\X_WORKITEM_ImgFill01.dwg"
        nFootDwg = "\\jwja-svr-10\drawfile\jvba\XCSI_FOOT_01.dwg"
        nJumpHead = 42 'was 60
        nJumpDiv = 18 'was 20
        nJumpWkCSI = 18 'WAS 20
        nJumpRow = 72 'was 72
        InsertJBlock "\\jwja-svr-10\drawfile\jvba\XCSI_HD_01.dwg", TblPT, "Model"

    End If
    
    
    'InsertJBlock "H:\drawfile\jvba\XCSI_HD_01.dwg", tblPT, "Model"
Else
    Exit Sub
End If

TblPT(1) = TblPT(1) - nJumpHead

'Set DB = OpenDatabase("H:\db\db_est\H_H_EST_2013_001.mdb")
Set DB = OpenDatabase("\\jwja-svr-10\jdb\db_est\x_EST_2013_001.mdb")

Dim varItm As Variant


With frmWorkItem.ListBox1
For il = 0 To .ListCount - 1
If .Selected(il) Then




    'xAssDiv = !assdiv
    'xAssID = ListBox1.List(il, 0)
    Debug.Print .Column(il, 0)
    Debug.Print .Column(0, il)
    xAssID = .Column(0, il)
    Debug.Print xAssID
    'strProjAss = "SELECT ASS.ASSID, ASS.ESTID, ASS.ASSDIV, ASS.ASSNO, ASS.ASSSUBDIV, ass.csi, ASS.ASSNAME, ASS.proj_no " _
    & "FROM ASS " _
    & "WHERE (((ASS.proj_no) = '" & frmWorkItem.seleproj & "'))" _
    & "ORDER BY ASS.ASSDIV, ASS.ASSNO"
    strProjAss = "SELECT ASS.ASSID, ASS.ESTID, ASS.ASSDIV, ASS.ASSNO, ASS.ASSSUBDIV, ASS.CSI, ASS.ASSNAME, ASS.proj_no " _
    & "FROM ASS " _
    & "WHERE (((ASS.ASSID) =" & xAssID & "))" _
    & "ORDER BY ASS.CSI;"

    
    
    Set rstProjAss = DB.OpenRecordset(strProjAss)
    Debug.Print rstProjAss.RecordCount
        If rstProjAss.RecordCount = 0 Then
            GoTo Exit_writeAssWorkItemImgCAD
        End If
    rstProjAss.MoveLast
    rstProjAss.MoveFirst
    Debug.Print rstProjAss.RecordCount
    Debug.Print rnProjAss
    rnProjAss = rstProjAss.RecordCount
        
        With rstProjAss
            Debug.Print !ASSID & "<<<<assid"
            Debug.Print !csi & "<<<<CSI"
            Debug.Print !ASSNAME & "<<<<ASSNAME"
            'xAssID = !assid
            'Debug.Print xAssID
            For j = 1 To rnProjAss
                xAssID = !ASSID
                Debug.Print xAssID
                Set blockRefObj = ThisDrawing.ModelSpace.InsertBlock _
                             (TblPT, nWkCsiDwg, 1, 1, 1, 0)
                Dim varAttributes2 As Variant
                varAttributes2 = blockRefObj.GetAttributes
                For iattr_ASS = LBound(varAttributes2) To UBound(varAttributes2)
                    Debug.Print varAttributes2(iattr_ASS).TagString
                    If varAttributes2(iattr_ASS).TagString = "XASSCSI" Then
                        If IsNull(!csi) = True Then
                            varAttributes2(iattr_ASS).textString = ""
                        Else
                            varAttributes2(iattr_ASS).textString = !csi
                            Debug.Print varAttributes2(iattr_ASS).textString
                        End If
                    End If
                    If varAttributes2(iattr_ASS).TagString = "XASSNAME" Then
                        Debug.Print !ASSNAME & "<<<< ASSNAME"
                        If IsNull(!ASSNAME) = True Then
                            varAttributes2(iattr_ASS).textString = ""
                        Else
                            '=DLookUp("csiname","csi","left(csi,2) = " & CStr([assdiv]))
                            varAttributes2(iattr_ASS).textString = !ASSNAME
                            Debug.Print varAttributes2(iattr_ASS).textString
    
                        End If
                    End If
                Next iattr_ASS
                TblPT(1) = TblPT(1) - nJumpWkCSI
                tempYpos = TblPT(1)
                strAssWorkItem = "SELECT WORK.ASSID, WORK.WKID, WORK.WKCSINO, WORK.WKCSINAME, WORK.WKNOTE ,WORK.WKNOTE_EX " _
                & "FROM ASS INNER JOIN [WORK] ON ASS.ASSID = WORK.ASSID " _
                & "WHERE (((WORK.ASSID) =" & xAssID & "))" _
                & "ORDER BY WORK.WKCSINO;"
    
                'Debug.Print xwkID
                Set rstAssWorkItem = DB.OpenRecordset(strAssWorkItem)
                Debug.Print rstAssWorkItem.RecordCount
                'Debug.Print strHDSet
                If rstAssWorkItem.RecordCount = 0 Then
                    GoTo Exit_writeAssWorkItemImgCAD
                End If
                rstAssWorkItem.MoveLast
                rstAssWorkItem.MoveFirst
                Debug.Print rstAssWorkItem.RecordCount
                Debug.Print rnAssWorkItem
                
                rnAssWorkItem = rstAssWorkItem.RecordCount
                With rstAssWorkItem
                    'xwkid = !wkid
                    rnAssWorkItem = rstAssWorkItem.RecordCount
                    Debug.Print xwkid
                    For k = 1 To rnAssWorkItem
                        xwkid = !wkid
                        Set blockRefObj = ThisDrawing.ModelSpace.InsertBlock _
                                     (TblPT, nRowDwg, 1, 1, 1, 0)
                        Debug.Print "k >>>>: " & k
    '**************************************************************************************
                        Dim imgPT(0 To 2) As Double
                        Dim fillPT(0 To 2) As Double
                        
                        Dim scalefactor, xSF As Double
                        Dim rotAngleInDegree As Double, rotAngle As Double
                        'Dim imageName As String
                        Dim imageName As String
                        Dim raster As AcadRasterImage
                        Dim imgheight As Variant
                        Dim imgwidth As Variant
                        Dim width As Double
                        Dim corner(0 To 2) As Double
                        Dim corner2(0 To 2) As Double
                        Dim prtImgNo, ImgTabx, ImgTaby As Integer
    '#########################################################################################
                        prtImgNo = 2
    '#########################################################################################
                        strWorkImg = "SELECT work.wkid, connwkpic.picid, PROJ_PIC.PICFULLNAME " _
                                & "FROM [WORK] INNER JOIN (connwkpic INNER JOIN PROJ_PIC ON connwkpic.picid = PROJ_PIC.PICID) " _
                                & "ON WORK.WKID = connwkpic.workid " _
                                & "WHERE (((work.wkid)=" & xwkid & "));"
    
                        Set rstWorkImg = DB.OpenRecordset(strWorkImg)
                        If rstWorkImg.RecordCount = 0 Then
                        GoTo NoImg
                        Else
                        rstWorkImg.MoveLast
                        rstWorkImg.MoveFirst
                        End If
                        'rstWorkImg.MoveLast
                        'rstWorkImg.MoveFirst

                        Debug.Print rstWorkImg.RecordCount
                        Debug.Print rnWorkImg
                        rnWorkImg = rstWorkImg.RecordCount
                        nImgFill = Round(rnWorkImg / 2, 0)
                        nImgFill = Round((rnWorkImg - (rnWorkImg - prtImgNo)) / 2, 0)
                        mgTop = rnWorkImg - (rnWorkImg - prtImgNo)
                        Debug.Print nImgFill & "<<<<<< nImgFill >>>>"
                        If frmWorkItem.PrintLarge = True Then
                            imgPT(0) = TblPT(0) + 6
                            imgPT(1) = TblPT(1) - 128 ' was 128
                            imgPT(2) = TblPT(2)
                        Else
                            imgPT(0) = TblPT(0) + 6
                            imgPT(1) = TblPT(1) - 68
                            imgPT(2) = TblPT(2)
                        End If
                        
 '++++++++++++++++++++++++++++++++++++++++++++++++++++++++++++++++++++++++++++++++++++++++
      '                  Do While Not rstWorkImg.EOF
                        
                        With rstWorkImg 'img1
                        'Do While Not rstWorkImg.EOF
                            rstWorkImg.MoveLast
                            rstWorkImg.MoveFirst
                            Debug.Print rstWorkImg.RecordCount
                            Debug.Print rnWorkImg
                            rnWorkImg = rstWorkImg.RecordCount
                            nImgFill = Round(rnWorkImg / 2, 0)
                            nImgFill = Round((rnWorkImg - (rnWorkImg - prtImgNo)) / 2, 0)
                            mgTop = rnWorkImg - (rnWorkImg - prtImgNo)
                            'For mg = 1 To rnWorkImg
                            'For mg = 1 To rnWorkImg - (rnWorkImg - prtImgNo)
                            For mg = 1 To mgTop
                                'If !PICFULLNAME <> "" Then
                                Debug.Print ">>>>> mg>>>>" & mg
                                
                                If mg = 2 Then
                                    If frmWorkItem.PrintLarge = True Then
                                        imgPT(0) = TblPT(0) + 132
                                    Else
                                        imgPT(0) = TblPT(0) + 66
                                    End If
                                End If
                                If frmWorkItem.ShowImage = True Then
                                
                                    'imageName = "C:\AutoCAD\sample\downtown.jpg"
                                    If IsNull(!picfullname) = False Then
                                    imageName = !picfullname
                                    Else
                                    imageName = ""
                                    End If
                                    Debug.Print mg & ": " & imageName
                                    corner(0) = imgPT(0) + 12
                                    corner(1) = imgPT(1) - 1
                                    corner(2) = imgPT(2)
                                    width = 48 '4' X 12
                                    CreateRstyle
                                    Set mtextObj = ThisDrawing.ModelSpace.AddMText(corner, width, !picid)
                                        mtextObj.StyleName = "R"
                                        mtextObj.Layer = "DI48"
                                        mtextObj.Color = acRed
                                        mtextObj.height = 2
                                        mtextObj.Update
                                        'Debug.Print !picfullname
                                    corner2(0) = imgPT(0) + 12
                                    corner2(1) = imgPT(1) + 12
                                    corner2(2) = imgPT(2)
                                    Set mtextObj = ThisDrawing.ModelSpace.AddMText(corner2, width, mg)
                                        'CreateARstyle
                                        mtextObj.StyleName = "R"
                                        mtextObj.Layer = "DEFPOINTS"
                                        mtextObj.height = 2
                                        mtextObj.Update
                                    'Debug.Print imageName
                                    'insertionPoint(0) = 2#: insertionPoint(1) = 2#: insertionPoint(2) = 0#
                                    
                                        
                                    If frmWorkItem.PrintLarge = True Then
                                    scalefactor = 96#
                                    'rotAngleInDegree = 0#
                                    'rotAngle = rotAngleInDegree * 3.141592 / 180#
                                    rotAngle = 0#
                                    imgScale = 96
                                    ImgTabx = 108
                                    ImgTaby = 128
                                    Else
                                    scalefactor = 48#
                                    rotAngle = 0#
                                    imgScale = 48
                                    ImgTabx = 66
                                    ImgTaby = 56
                                    End If
                                    
                                    
                                    ' Creates a raster image in model space
                                    'If !fximgname <> "" Then
                                        Set raster = ThisDrawing.ModelSpace.AddRaster(imageName, imgPT, scalefactor, rotAngle)
                                        With raster
                                            imgheight = raster.ImageHeight
                                            imgwidth = raster.ImageWidth
                                                If imgheight > imgScale Then
                                                    xSF = (imgScale / imgheight) * imgScale
                                                    Debug.Print "xSF: " & xSF * imgScale
                                                     raster.scalefactor = xSF
                                                End If
                                        End With
                                    End If
                                'End If
                            
                            'imgPT(1) = imgPT(1) - nJumpRow
                            If ((mg Mod 2) = 0) Then 'even
                            
                            Debug.Print mg Mod 2 & "see mod"
                            
                                imgPT(0) = TblPT(0) + ImgTabx
                                
                                imgPT(1) = imgPT(1) - ImgTaby
                            Else
                                imgPT(0) = TblPT(0) + 6
                                'imgPT(1) = imgPT(1) - 54
                            End If
                            If rnWorkImg < 2 Then
                            'Exit Do
                            Exit For
                            End If
                            .MoveNext
                            Next mg
                            Debug.Print "test"
                            '.MoveNext
                        'Loop
                        End With 'img1
     '                   Loop
 '++++++++++++++++++++++++++++++++++++++++++++++++++++++++++++++++++++++++++++++++++++++++
NoImg:
    '**************************************************************************************
                        Dim varAttributes3 As Variant
                        varAttributes3 = blockRefObj.GetAttributes
    
                        For iattr_WKCSI = LBound(varAttributes3) To UBound(varAttributes3)
                            Debug.Print varAttributes3(iattr_WKCSI).TagString
                            If varAttributes3(iattr_WKCSI).TagString = "XWKCSINO" Then
                                If IsNull(!wkcsino) = True Then
                                    varAttributes3(iattr_WKCSI).textString = ""
                                Else
                                    varAttributes3(iattr_WKCSI).textString = !wkcsino
                                End If
                            End If
                            If varAttributes3(iattr_WKCSI).TagString = "XWKCSINAME" Then
                                If IsNull(!WKCSINAME) = True Then
                                    varAttributes3(iattr_WKCSI).textString = ""
                                Else
                                    varAttributes3(iattr_WKCSI).textString = !WKCSINAME
                                End If
                            End If
                            If varAttributes3(iattr_WKCSI).TagString = "XNOTE1" Then
                                If IsNull(!WKNOTE_EX) = True Then
                                    varAttributes3(iattr_WKCSI).textString = ""
                                Else
                                    varAttributes3(iattr_WKCSI).textString = SEPTEXT2(!WKNOTE_EX, 1, 5, 46)
                                    'varAttributes3(iattr_WKCSI).TextString = !WKNOTE_EX
                                End If
                            End If
                            If varAttributes3(iattr_WKCSI).TagString = "XNOTE2" Then
                                If IsNull(!WKNOTE_EX) = True Then
                                    varAttributes3(iattr_WKCSI).textString = ""
                                Else
                                    varAttributes3(iattr_WKCSI).textString = SEPTEXT2(!WKNOTE_EX, 2, 5, 46)
                                End If
                            End If
                            If varAttributes3(iattr_WKCSI).TagString = "XNOTE3" Then
                                If IsNull(!WKNOTE_EX) = True Then
                                    varAttributes3(iattr_WKCSI).textString = ""
                                Else
                                    varAttributes3(iattr_WKCSI).textString = SEPTEXT2(!WKNOTE_EX, 3, 5, 46)
                                End If
                            End If
                              If varAttributes3(iattr_WKCSI).TagString = "XNOTE4" Then
                                If IsNull(!WKNOTE_EX) = True Then
                                    varAttributes3(iattr_WKCSI).textString = ""
                                Else
                                    varAttributes3(iattr_WKCSI).textString = SEPTEXT2(!WKNOTE_EX, 4, 5, 46)
                                End If
                            End If
                              If varAttributes3(iattr_WKCSI).TagString = "XNOTE5" Then
                                If IsNull(!WKNOTE_EX) = True Then
                                    varAttributes3(iattr_WKCSI).textString = ""
                                Else
                                    varAttributes3(iattr_WKCSI).textString = SEPTEXT2(!WKNOTE_EX, 5, 5, 46)
                                End If
                            End If
                            '#################################################################################
                            If varAttributes3(iattr_WKCSI).TagString = "XNWNOTE1" Then
                                If IsNull(!WKNOTE) = True Then
                                    varAttributes3(iattr_WKCSI).textString = ""
                                Else
                                    varAttributes3(iattr_WKCSI).textString = SEPTEXT2(!WKNOTE, 1, 5, 46)
                                End If
                            End If
                            If varAttributes3(iattr_WKCSI).TagString = "XNWNOTE2" Then
                                If IsNull(!WKNOTE) = True Then
                                    varAttributes3(iattr_WKCSI).textString = ""
                                Else
                                    varAttributes3(iattr_WKCSI).textString = SEPTEXT2(!WKNOTE, 2, 5, 46)
                                End If
                            End If
                            If varAttributes3(iattr_WKCSI).TagString = "XNWNOTE3" Then
                                If IsNull(!WKNOTE) = True Then
                                    varAttributes3(iattr_WKCSI).textString = ""
                                Else
                                    varAttributes3(iattr_WKCSI).textString = SEPTEXT2(!WKNOTE, 3, 5, 46)
                                End If
                            End If
                            If varAttributes3(iattr_WKCSI).TagString = "XNWNOTE4" Then
                                If IsNull(!WKNOTE) = True Then
                                    varAttributes3(iattr_WKCSI).textString = ""
                                Else
                                    varAttributes3(iattr_WKCSI).textString = SEPTEXT2(!WKNOTE, 4, 5, 46)
                                End If
                            End If
                            If varAttributes3(iattr_WKCSI).TagString = "XNWNOTE5" Then
                                If IsNull(SEPTEXT2(!WKNOTE, 4, 5, 60)) = True Then
                                'If Len(SEPTEXT2(!WKNOTE, 5, 5, 60)) > 1 Then
                                    varAttributes3(iattr_WKCSI).textString = ""
                                Else
                                    varAttributes3(iattr_WKCSI).textString = SEPTEXT2(!WKNOTE, 5, 5, 46)
                                End If
                            End If
    '**************************************************************************************
                            If varAttributes3(iattr_WKCSI).TagString = "XBY1" Then
                                Debug.Print WRITEWORKBY(!wkid)
                                If IsNull(WRITEWORKBY(!wkid)) = True Then
                                    varAttributes3(iattr_WKCSI).textString = ""
                                Else
                                    varAttributes3(iattr_WKCSI).textString = SEPTEXT2(WRITEWORKBY(!wkid), 1, 2, 20)
                                End If
                            End If
                            If varAttributes3(iattr_WKCSI).TagString = "XBY2" Then
                                If IsNull(WRITEWORKBY(!wkid)) = True Then
                                    varAttributes3(iattr_WKCSI).textString = ""
                                Else
                                    varAttributes3(iattr_WKCSI).textString = SEPTEXT2(WRITEWORKBY(!wkid), 2, 2, 20)
                                End If
                            End If
                            If varAttributes3(iattr_WKCSI).TagString = "XACT1" Then
                                If IsNull(printAction(!wkid)) = True Then
                                    varAttributes3(iattr_WKCSI).textString = ""
                                Else
                                    varAttributes3(iattr_WKCSI).textString = SEPTEXT2(printAction(!wkid), 1, 2, 20)
                                End If
                            End If
                            If varAttributes3(iattr_WKCSI).TagString = "XACT2" Then
                                If IsNull(printAction(!wkid)) = True Then
                                    varAttributes3(iattr_WKCSI).textString = ""
                                Else
                                    varAttributes3(iattr_WKCSI).textString = SEPTEXT2(printAction(!wkid), 2, 2, 20)
                                End If
                            End If
    '**************************************************************************************
                        Dim CsiPos(0 To 2) As Double
                        CsiPos(0) = TblPT(0) - 360
                        CsiPos(1) = TblPT(1)
                        CsiPos(2) = TblPT(2)
                        width = 240 '4' X 12
                        CSILabel = UCase(!wkcsino & "-" & !WKNOTE_EX)
                        Set mtextObj = ThisDrawing.ModelSpace.AddMText(CsiPos, width, CSILabel)
                            mtextObj.StyleName = "R"
                            mtextObj.height = 4
                            mtextObj.Layer = "DI48"
                            mtextObj.Update
                        CsiPos(0) = CsiPos(0) - 240
                        width = 84 '4' X 12
                        If IsNull(!wkcsino) = False Then
                        Set mtextObj = ThisDrawing.ModelSpace.AddMText(CsiPos, width, !wkcsino)
                            mtextObj.StyleName = "R"
                            mtextObj.height = 4
                            mtextObj.Layer = "DI48"
                            mtextObj.Update
                        End If
    '**************************************************************************************
                        Next iattr_WKCSI
                        
    '******* FILL DWG ************** GOT IT TO WORK ON 11/11/12 *****************************
    
                        Debug.Print TblPT(0) & " : " & TblPT(1) & " : " & TblPT(2) & "<<<<<<< tblPT"
                        fillPT(0) = TblPT(0)
                        fillPT(1) = TblPT(1) - nJumpRow
                        fillPT(2) = TblPT(2)
                        Debug.Print fillPT(0) & " : " & fillPT(1) & " : " & fillPT(2) & "<<<<<< fillPT"
                        Debug.Print tempYpos
                            For iFill = 1 To nImgFill - 1
                                Set blockRefObj = ThisDrawing.ModelSpace.InsertBlock _
                                                    (fillPT, nImgFillDwg, 1, 1, 1, 0)
                                fillPT(1) = fillPT(1) - ImgTaby
                            Next iFill
                            If nImgFill <= 1 Then
                                TblPT(1) = TblPT(1) - nJumpRow
                            Else
                                TblPT(1) = TblPT(1) - nJumpRow - ((nImgFill - 1) * ImgTaby)
                            End If
     '***** FILL DWG *************************************************************************
                        .MoveNext
                    Next k 'rnAssWorkItem
                    '.MoveNext
                End With
                'rstWorkItem.Close
                .MoveNext
            Next j 'rnProjAss
            
    End With 'rstProjAss first with
End If
Next il
End With
rstProjAss.Close
Set blockRefObj = ThisDrawing.ModelSpace.InsertBlock _
                                             (TblPT, nFootDwg, 1, 1, 1, 0)
''ThisDrawing.SelectionSets.Item("hdwrsched").Delete
'rstProjDiv.Close
'rstProjAss.Close
'rstWorkItem.Close


'RsHDwrSet.Close
Set DB = Nothing

''Else

''ThisDrawing.SelectionSets.Item("hdwrsched").Delete
'no attribute block, inform the user
'

'MsgBox "Inserted block! Re-run this program.", vbCritical, "JWJA"

'delete the selection set
'ThisDrawing.SelectionSets.Item("TBLK").Delete

''End If

'Set MTextObj = ThisDrawing.ModelSpace.AddMText(corner, width, text)

''ThisDrawing.SelectionSets.Item("hdwrsched").Delete


Exit_writeAssWorkItemImgCAD:
frmWorkItem.Hide

End Sub

Public Sub writeWorkItemImg()


Dim DB As Database
Dim rstProjDiv, rstProjAss, rstAssWorkItem, rstWorkImg As Recordset
Dim strProjDiv, strProjAss, strAssWorkItem, strWorkImg, txtRow As String
Dim rnProjDiv, rnProjAss, rnAssWorkItem, rnWorkImg As Integer     'ProjSet no.
'Dim rcArray As Variant
Dim TblPT(0 To 2) As Double
Dim tblPT2(0 To 2) As Double
Dim tmpArrayAss(0 To 1) As Double

Dim tblWidth As Double
Dim txtHt As Double
Dim textObj As AcadText
Dim attributeObj As AcadAttribute
Dim height As Double
Dim mode As Long
Dim prompt As String

'**********IMG********************
Dim nHeadDwg, nDivDwg, nWkCsiDwg, nRowDwg, nFootDwg, nImgDwg As Variant
Dim nJumpHead, nJumpGroup, nJumpRow As Integer
'**********IMG********************

'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

'Dim xHDWRSETID, i, iatHG, rnHDWR, k, iatHW As Integer
Dim xDivNo, xAssID, i, iDiv, irnDiv, irnAss, j, k, irnWorkItem, iattr_DIV, iattr_ASS, iattr_WORKITEM As Integer
Dim mg, iattr_Img As Integer



frmWorkItem.ListBox1.Clear
CreateCNstyle






'strHDSet = "SELECT HDWRCONN.HDWRSETID, " _
                        & "HDWRCONN.SETQTY, HDWR.TYPE, HDWR.CAT, HDWR.MFGR, HDWR.FIN, HDWR.HDWRNOTE, HDWR.HDIMGNAME, HDWR.HDWRDESC " _
                        & "FROM HDWR INNER JOIN HDWRCONN ON HDWR.HDID = HDWRCONN.HDID " _
                        & "WHERE (((HDWRCONN.HDWRSETID)=" & xHDWRSETID & "));"





TblPT(0) = 0: TblPT(1) = 0: TblPT(2) = 0
tblPT2(0) = -300: tblPT2(1) = 0: tblPT2(2) = 0
txtHt = 4
txtRow = ""
mode = acAttributeModeVerify

''InsertJBlock "e:\drawfile\jvba\XHDWRHEAD01.dwg", tblPT, "Model"
'ThisDrawing.ModelSpace.InsertBlock tblPT, "e:\drawfile\jvba\XHDWRHEAD02.dwg", 1, 1, 1, 0
'InsertJBlock "e:\drawfile\jvba\XHDWRGPROW02.dwg", tblPT2, "Model"
'InsertJBlock "e:\drawfile\jvba\XHDWRROW02.dwg", tblPT2, "Model"
'InsertJBlock "e:\drawfile\jvba\XHDWRFOOT02.dwg", tblPT2, "Model"

'ThisDrawing.SelectionSets.Item("XHDWRGPROW01").Delete
'ThisDrawing.SelectionSets.Item("XHDWRROW01").Delete

If frmWorkItem.ShowImage = True Then
    nHeadDwg = "\\jwja-svr-10\drawfile\jvba\X_WORKITEM_HEAD01.dwg"
    'nGroupDwg = "H:\drawfile\jvba\XHDWRGPROW03.dwg"
    nDivDwg = "\\jwja-svr-10\drawfile\jvba\X_WORKITEM_DIV_ROW01.dwg"
    nWkCsiDwg = "\\jwja-svr-10\drawfile\jvba\X_WORKITEM_WKCSI_ROW01.dwg"
    nRowDwg = "\\jwja-svr-10\drawfile\jvba\X_WORKITEM_ROW01.dwg"
    nImgFillDwg = "\\jwja-svr-10\drawfile\jvba\X_WORKITEM_ImgFill01.dwg"
    nFootDwg = "\\jwja-svr-10\drawfile\jvba\X_WORKITEM_FOOT01.dwg"
    nJumpHead = 60 'was 24
    nJumpDiv = 24 'was 66
    nJumpWkCSI = 24
    nJumpRow = 72 'was 60
    InsertJBlock "\\jwja-svr-10\drawfile\jvba\X_WORKITEM_HEAD01.dwg", TblPT, "Model"
Else
    nHeadDwg = "\\jwja-svr-10\drawfile\jvba\X_WORKITEM_HEAD02.dwg"
    'nGroupDwg = "H:\drawfile\jvba\XHDWRGPROW03.dwg"
    nDivDwg = "\\jwja-svr-10\drawfile\jvba\X_WORKITEM_DIV_ROW02.dwg"
    nWkCsiDwg = "\\jwja-svr-10\drawfile\jvba\X_WORKITEM_WKCSI_ROW02.dwg"
    nRowDwg = "\\jwja-svr-10\drawfile\jvba\X_WORKITEM_ROW02.dwg"
    nImgFillDwg = "\\jwja-svr-10\drawfile\jvba\X_WORKITEM_ImgFill03.dwg"
    nFootDwg = "\\jwja-svr-10\drawfile\jvba\X_WORKITEM_FOOT02.dwg"
    nJumpHead = 60 'was 24
    nJumpDiv = 24 'was 66
    nJumpWkCSI = 24
    nJumpRow = 72 'was 60
    InsertJBlock "\\jwja-svr-10\drawfile\jvba\X_WORKITEM_HEAD02.dwg", TblPT, "Model"
End If

TblPT(1) = TblPT(1) - nJumpHead

'Set DB = OpenDatabase("H:\db\db_est\H_H_EST_2013_001.mdb")
Set DB = OpenDatabase("\\jwja-svr-10\jdb\Jdb\db_est\H_H_EST_2013_001.mdb")

strProjDiv = "SELECT ASS.ASSDIV, DIV.DIVNAME, ASS.proj_no " _
& "FROM ASS INNER JOIN DIV ON ASS.ASSDIV = DIV.DIVNO " _
& "GROUP BY ASS.ASSDIV, DIV.DIVNAME, ASS.proj_no " _
& "HAVING (((ASS.proj_no)='" & frmWorkItem.seleproj & "'))"

RecordSets:
Set rstProjDiv = DB.OpenRecordset(strProjDiv, dbOpenDynaset)

'Set rstProjAss = DB.OpenRecordset(strProjAss, dbOpenDynaset)
tempcount = rstProjDiv.RecordCount
If rstProjDiv.RecordCount = 0 Then
    GoTo Exit_writeWorkItemImg
End If

rstProjDiv.MoveLast
rstProjDiv.MoveFirst
rnProjDiv = rstProjDiv.RecordCount
Debug.Print rnProjAss

With rstProjDiv
    For i = 1 To rnProjDiv
         xDivNo = !assdiv
         Set blockRefObj = ThisDrawing.ModelSpace.InsertBlock _
                     (TblPT, nDivDwg, 1, 1, 1, 0)
        '******************************
          'Get the block's attributes
                Dim varAttributes As Variant
                varAttributes = blockRefObj.GetAttributes
                    For iattr_DIV = LBound(varAttributes) To UBound(varAttributes)
                        Debug.Print varAttributes(iattr_DIV).TagString
                        If varAttributes(iattr_DIV).TagString = "XDIVNO" Then
                            If IsNull(!assdiv) = True Then
                                varAttributes(iattr_DIV).textString = ""
                            Else
                                varAttributes(iattr_DIV).textString = !assdiv
                                Debug.Print varAttributes(iattr_DIV).textString
                            End If

                        End If
                        If varAttributes(iattr_DIV).TagString = "XDIVNAME" Then
                            If IsNull(!DIVNAME) = True Then
                                varAttributes(iattr_DIV).textString = ""
                            Else
                                '=DLookUp("csiname","csi","left(csi,2) = " & CStr([assdiv]))
                                varAttributes(iattr_DIV).textString = !DIVNAME
                                Debug.Print varAttributes(iattr_DIV).textString

                            End If

                        End If
                    Next iattr_DIV
                    TblPT(1) = TblPT(1) - nJumpDiv
                    xAssDiv = !assdiv
                    strProjAss = "SELECT ASS.ASSID, ASS.ESTID, ASS.ASSDIV, ASS.ASSNO, ASS.ASSSUBDIV, ass.csi, ASS.ASSNAME, ASS.proj_no " _
                    & "FROM ASS " _
                    & "WHERE (((ASS.proj_no) = '" & frmWorkItem.seleproj & "'))" _
                    & "ORDER BY ASS.ASSDIV, ASS.ASSNO"

                    'Debug.Print xAssID
                    Set rstProjAss = DB.OpenRecordset(strProjAss)
                    Debug.Print rstProjAss.RecordCount
                    'Debug.Print xAssID
                    'Debug.Print strHDSet
                        If rstProjAss.RecordCount = 0 Then
                            GoTo Exit_writeWorkItemImg
                        End If
                        rstProjAss.MoveLast
                        rstProjAss.MoveFirst
                        Debug.Print rstProjAss.RecordCount
                        Debug.Print rnProjAss
                        rnProjAss = rstProjAss.RecordCount
                        
                        With rstProjAss
                            Debug.Print !ASSID & "<<<<assid"
                            Debug.Print !csi & "<<<<CSI"
                            Debug.Print !ASSNAME & "<<<<ASSNAME"
                            'xAssID = !assid
                            'Debug.Print xAssID
                            For j = 1 To rnProjAss
                                xAssID = !ASSID
                                Debug.Print xAssID
                                Set blockRefObj = ThisDrawing.ModelSpace.InsertBlock _
                                             (TblPT, nWkCsiDwg, 1, 1, 1, 0)
                                Dim varAttributes2 As Variant
                                varAttributes2 = blockRefObj.GetAttributes
                                For iattr_ASS = LBound(varAttributes2) To UBound(varAttributes2)
                                    Debug.Print varAttributes2(iattr_ASS).TagString
                                    If varAttributes2(iattr_ASS).TagString = "XASSCSI" Then
                                        If IsNull(!csi) = True Then
                                            varAttributes2(iattr_ASS).textString = ""
                                        Else
                                            varAttributes2(iattr_ASS).textString = !csi
                                            Debug.Print varAttributes(iattr_ASS).textString
                                        End If
                                    End If
                                    If varAttributes2(iattr_ASS).TagString = "XASSNAME" Then
                                        Debug.Print !ASSNAME & "<<<< ASSNAME"
                                        If IsNull(!ASSNAME) = True Then
                                            varAttributes2(iattr_ASS).textString = ""
                                        Else
                                            '=DLookUp("csiname","csi","left(csi,2) = " & CStr([assdiv]))
                                            varAttributes2(iattr_ASS).textString = !ASSNAME
                                            Debug.Print varAttributes(iattr_ASS).textString

                                        End If
                                    End If
                                Next iattr_ASS
                                TblPT(1) = TblPT(1) - nJumpWkCSI
                                strAssWorkItem = "SELECT WORK.ASSID, WORK.WKID, WORK.WKCSINO, WORK.WKCSINAME, WORK.WKNOTE ,WORK.WKNOTE_EX " _
                                & "FROM ASS INNER JOIN [WORK] ON ASS.ASSID = WORK.ASSID " _
                                & "WHERE (((WORK.ASSID) =" & xAssID & "))" _
                                & "ORDER BY WORK.WKCSINO;"

                                'Debug.Print xwkID
                                Set rstAssWorkItem = DB.OpenRecordset(strAssWorkItem)
                                Debug.Print rstAssWorkItem.RecordCount
                                'Debug.Print strHDSet
                                If rstAssWorkItem.RecordCount = 0 Then
                                    GoTo Exit_writeWorkItemImg
                                End If
                                rstAssWorkItem.MoveLast
                                rstAssWorkItem.MoveFirst
                                Debug.Print rstAssWorkItem.RecordCount
                                Debug.Print rnAssWorkItem
                                
                                rnAssWorkItem = rstAssWorkItem.RecordCount
                                With rstAssWorkItem
                                    'xwkid = !wkid
                                    Debug.Print xwkid
                                    For k = 1 To rnAssWorkItem
                                        xwkid = !wkid
                                        Set blockRefObj = ThisDrawing.ModelSpace.InsertBlock _
                                                     (TblPT, nRowDwg, 1, 1, 1, 0)

'**************************************************************************************
                                        Dim imgPT(0 To 2) As Double
                                        Dim fillPT(0 To 2) As Double
                                        
                                        Dim scalefactor, xSF As Double
                                        Dim rotAngleInDegree As Double, rotAngle As Double
                                        'Dim imageName As String
                                        Dim imageName As String
                                        Dim raster As AcadRasterImage
                                        Dim imgheight As Variant
                                        Dim imgwidth As Variant
                                        Dim width As Double
                                        Dim corner(0 To 2) As Double
                                        Dim corner2(0 To 2) As Double
                                        

                                        
                                        strWorkImg = "SELECT work.wkid, connwkpic.picid, PROJ_PIC.PICFULLNAME " _
                                                & "FROM [WORK] INNER JOIN (connwkpic INNER JOIN PROJ_PIC ON connwkpic.picid = PROJ_PIC.PICID) " _
                                                & "ON WORK.WKID = connwkpic.workid " _
                                                & "WHERE (((work.wkid)=" & xwkid & "));"

                                        Set rstWorkImg = DB.OpenRecordset(strWorkImg)
                                        If rstWorkImg.RecordCount = 0 Then
                                        Exit For
                                        Else
                                        rstWorkImg.MoveLast
                                        rstWorkImg.MoveFirst
                                        End If
                                        Debug.Print rstWorkImg.RecordCount
                                        Debug.Print rnWorkImg
                                        rnWorkImg = rstWorkImg.RecordCount
                                        nImgFill = Round(rnWorkImg / 2, 0)
                                        Debug.Print nImgFill & "<<<<<< nImgFill >>>>"
                                            imgPT(0) = TblPT(0) + 6
                                            imgPT(1) = TblPT(1) - 68
                                            imgPT(2) = TblPT(2)

                                        With rstWorkImg 'img1
                                            For mg = 1 To rnWorkImg
                                                'If !PICFULLNAME <> "" Then
                                                If mg = 2 Then
                                                    imgPT(0) = TblPT(0) + 66
                                                End If
                                                    If frmWorkItem.ShowImage = True Then
                                                
                                                    'imageName = "C:\AutoCAD\sample\downtown.jpg"
                                                    If IsNull(!picfullname) = False Then
                                                    imageName = !picfullname
                                                    Else
                                                    imageName = ""
                                                    End If
                                                    Debug.Print mg & ": " & imageName
                                                    corner(0) = imgPT(0) + 12
                                                    corner(1) = imgPT(1) - 4
                                                    corner(2) = imgPT(2)
                                                    width = 48 '4' X 12
                                                    Set mtextObj = ThisDrawing.ModelSpace.AddMText(corner, width, !picid)
                                                        mtextObj.StyleName = "R"
                                                        mtextObj.height = 2
                                                        mtextObj.Update
                                                    corner2(0) = imgPT(0) + 12
                                                    corner2(1) = imgPT(1) + 12
                                                    corner2(2) = imgPT(2)
                                                    Set mtextObj = ThisDrawing.ModelSpace.AddMText(corner2, width, mg)
                                                        CreateARstyle
                                                        mtextObj.StyleName = "ar"
                                                        mtextObj.height = 2
                                                        mtextObj.Update
                                                    'Debug.Print imageName
                                                    'insertionPoint(0) = 2#: insertionPoint(1) = 2#: insertionPoint(2) = 0#
                                                    
                                                        
                                                       
                                                    scalefactor = 48#
                                                    'rotAngleInDegree = 0#
                                                    'rotAngle = rotAngleInDegree * 3.141592 / 180#
                                                    rotAngle = 0#
                                                    
                                                    
                                                    
                                                    ' Creates a raster image in model space
                                                    'If !fximgname <> "" Then
                                                        Set raster = ThisDrawing.ModelSpace.AddRaster(imageName, imgPT, scalefactor, rotAngle)
                                                        With raster
                                                            imgheight = raster.ImageHeight
                                                            imgwidth = raster.ImageWidth
                                                                If imgheight > 48 Then
                                                                    xSF = (48 / imgheight) * 48
                                                                    Debug.Print "xSF: " & xSF * 48
                                                                     raster.scalefactor = xSF
                                                                End If
                                                        End With
                                                    End If
                                                'End If
                                            
                                            'imgPT(1) = imgPT(1) - nJumpRow
                                            If ((mg Mod 2) = 0) Then 'even
                                            
                                            Debug.Print mg Mod 2 & "see mod"
                                            
                                                imgPT(0) = TblPT(0) + 66
                                                imgPT(1) = imgPT(1) - 56
                                            Else
                                                imgPT(0) = TblPT(0) + 6
                                                'imgPT(1) = imgPT(1) - 54
                                            End If
                                            
                                            .MoveNext
                                            Next mg
                                            '.MoveNext
                                        End With 'img1
'**************************************************************************************
                                        Dim varAttributes3 As Variant
                                        varAttributes3 = blockRefObj.GetAttributes

                                        For iattr_WKCSI = LBound(varAttributes3) To UBound(varAttributes3)
                                            Debug.Print varAttributes3(iattr_WKCSI).TagString
                                            If varAttributes3(iattr_WKCSI).TagString = "XWKCSINO" Then
                                                If IsNull(!wkcsino) = True Then
                                                    varAttributes3(iattr_WKCSI).textString = ""
                                                Else
                                                    varAttributes3(iattr_WKCSI).textString = !wkcsino
                                                End If
                                            End If
                                            If varAttributes3(iattr_WKCSI).TagString = "XWKCSINAME" Then
                                                If IsNull(!WKCSINAME) = True Then
                                                    varAttributes3(iattr_WKCSI).textString = ""
                                                Else
                                                    varAttributes3(iattr_WKCSI).textString = !WKCSINAME
                                                End If
                                            End If
                                            If varAttributes3(iattr_WKCSI).TagString = "XNOTE1" Then
                                                If IsNull(!WKNOTE_EX) = True Then
                                                    varAttributes3(iattr_WKCSI).textString = ""
                                                Else
                                                    varAttributes3(iattr_WKCSI).textString = SEPTEXT2(!WKNOTE_EX, 1, 5, 48)
                                                End If
                                            End If
                                            If varAttributes3(iattr_WKCSI).TagString = "XNOTE2" Then
                                                If IsNull(!WKNOTE_EX) = True Then
                                                    varAttributes3(iattr_WKCSI).textString = ""
                                                Else
                                                    varAttributes3(iattr_WKCSI).textString = SEPTEXT2(!WKNOTE_EX, 2, 5, 48)
                                                End If
                                            End If
                                            If varAttributes3(iattr_WKCSI).TagString = "XNOTE2" Then
                                                If IsNull(!WKNOTE_EX) = True Then
                                                    varAttributes3(iattr_WKCSI).textString = ""
                                                Else
                                                    varAttributes3(iattr_WKCSI).textString = SEPTEXT2(!WKNOTE_EX, 2, 5, 48)
                                                End If
                                            End If
                                                     If varAttributes3(iattr_WKCSI).TagString = "XNOTE3" Then
                                                If IsNull(!WKNOTE_EX) = True Then
                                                    varAttributes3(iattr_WKCSI).textString = ""
                                                Else
                                                    varAttributes3(iattr_WKCSI).textString = SEPTEXT2(!WKNOTE_EX, 3, 5, 48)
                                                End If
                                            End If
                                              If varAttributes3(iattr_WKCSI).TagString = "XNOTE4" Then
                                                If IsNull(!WKNOTE_EX) = True Then
                                                    varAttributes3(iattr_WKCSI).textString = ""
                                                Else
                                                    varAttributes3(iattr_WKCSI).textString = SEPTEXT2(!WKNOTE_EX, 4, 5, 48)
                                                End If
                                            End If
                                              If varAttributes3(iattr_WKCSI).TagString = "XNOTE5" Then
                                                If IsNull(!WKNOTE_EX) = True Then
                                                    varAttributes3(iattr_WKCSI).textString = ""
                                                Else
                                                    varAttributes3(iattr_WKCSI).textString = SEPTEXT2(!WKNOTE_EX, 5, 5, 48)
                                                End If
                                            End If
                                            If varAttributes3(iattr_WKCSI).TagString = "XNWNOTE1" Then
                                                If IsNull(!WKNOTE) = True Then
                                                    varAttributes3(iattr_WKCSI).textString = ""
                                                Else
                                                    varAttributes3(iattr_WKCSI).textString = SEPTEXT2(!WKNOTE, 1, 5, 48)
                                                End If
                                            End If
                                            If varAttributes3(iattr_WKCSI).TagString = "XNWNOTE2" Then
                                                If IsNull(!WKNOTE) = True Then
                                                    varAttributes3(iattr_WKCSI).textString = ""
                                                Else
                                                    varAttributes3(iattr_WKCSI).textString = SEPTEXT2(!WKNOTE, 2, 5, 48)
                                                End If
                                            End If
                                            If varAttributes3(iattr_WKCSI).TagString = "XNWNOTE3" Then
                                                If IsNull(!WKNOTE) = True Then
                                                    varAttributes3(iattr_WKCSI).textString = ""
                                                Else
                                                    varAttributes3(iattr_WKCSI).textString = SEPTEXT2(!WKNOTE, 3, 5, 48)
                                                End If
                                            End If
                                            If varAttributes3(iattr_WKCSI).TagString = "XNWNOTE4" Then
                                                If IsNull(!WKNOTE) = True Then
                                                    varAttributes3(iattr_WKCSI).textString = ""
                                                Else
                                                    varAttributes3(iattr_WKCSI).textString = SEPTEXT2(!WKNOTE, 4, 5, 48)
                                                End If
                                            End If
                                            If varAttributes3(iatHW).TagString = "XNWNOTE5" Then
                                                If IsNull(SEPTEXT2(!WKNOTE, 5, 5, 48)) = True Then
                                                    varAttributes3(iatHW).textString = ""
                                                Else
                                                    varAttributes3(iatHW).textString = SEPTEXT2(!WKNOTE, 5, 5, 48)
                                                End If
                                            End If
                                          

'**************************************************************************************
                                        Next iattr_WKCSI
                                            fillPT(1) = TblPT(1) - 16
                                            'For iFill = 3 To rnWorkImg - 1
                                                fillPT(0) = TblPT(0)
                                                fillPT(1) = fillPT(1) - 72
                                                fillPT(2) = TblPT(2)
                                                'If ((iFill Mod 2) = 0) Then
                                                    'Debug.Print "Even"
                                            For iFill = 2 To nImgFill
                                                
                                                    
                                                    Set blockRefObj = ThisDrawing.ModelSpace.InsertBlock _
                                                                        (fillPT, nImgFillDwg, 1, 1, 1, 0)
                                                    fillPT(1) = fillPT(1) - 56
                                            Next iFill
                                            
                                            If nImgFill <= 1 Then
                                                TblPT(1) = TblPT(1) - nJumpRow
                                            Else
                                                TblPT(1) = TblPT(1) - nJumpRow - ((nImgFill - 1) * 56)
                                                                                                            
                                                

                                            End If
                                        .MoveNext
                                    Next k 'rnAssWorkItem
                                    '.MoveNext
                                End With
                                'rstWorkItem.Close
                                .MoveNext
                            Next j 'rnProjAss
                            
                            End With 'rstProjAss
                   'rstProjAss.Close
                'attributeObj.Update
        
                '************************************************
                'txtRow = !drgno & Chr(9) & !oldsize
                'Set textObj = ThisDrawing.ModelSpace.AddText(txtRow, tblPT, txtHT)
                '******************************************************
                'textObj.StyleName = "cn"
                'textObj.Update
                Debug.Print "iattr_Div :" & iattr_DIV
        TblPT(1) = TblPT(1)
        .MoveNext
        
    Next i
End With
rstProjAss.Close
Set blockRefObj = ThisDrawing.ModelSpace.InsertBlock _
                                             (TblPT, nFootDwg, 1, 1, 1, 0)
''ThisDrawing.SelectionSets.Item("hdwrsched").Delete
rstProjDiv.Close
'rstProjAss.Close
'rstWorkItem.Close


'RsHDwrSet.Close
Set DB = Nothing

''Else

''ThisDrawing.SelectionSets.Item("hdwrsched").Delete
'no attribute block, inform the user
'

'MsgBox "Inserted block! Re-run this program.", vbCritical, "JWJA"

'delete the selection set
'ThisDrawing.SelectionSets.Item("TBLK").Delete

''End If

'Set MTextObj = ThisDrawing.ModelSpace.AddMText(corner, width, text)

''ThisDrawing.SelectionSets.Item("hdwrsched").Delete


Exit_writeWorkItemImg:
frmWorkItem.Hide

End Sub

Attribute VB_Name = "WriteNotes"
Function WriteCSILabel(TblPT As Variant, mCSI As String, mWKCSINAME As String)
Dim CsiPos(0 To 2) As Variant
Dim CSILabel As String
Dim width As Integer
Dim textObj As AcadText
Dim mtextObj As AcadMText

CsiPos(0) = TblPT(0) - 120
CsiPos(1) = TblPT(1)
CsiPos(2) = TblPT(2)
width = 48 '4' X 12
CSILabel = mCSI & "-" & mWKCSINAME
Set mtextObj = ThisDrawing.ModelSpace.AddMText(CsiPos, width, CSILabel)
    mtextObj.StyleName = "R"
    mtextObj.height = 4
    mtextObj.Update

End Function
Function WRITEWORKBY(mWkID As Variant)

    
Dim ctl As Control
Dim varItm As Variant
Dim dbs As Database, rst As Object
Dim strSQL, tmpWorkby As String
    ' Return reference to current database.
Set dbs = OpenDatabase("\\jwja-svr-10\Jdb\db_est\X_EST_2013_001.mdb")
    ' Open recordset on Employees table.
    'Set rst = dbs.OpenRecordset("ASSit", dbOpenDynaset)
Debug.Print mWkID
strSQL = "SELECT connwkby.connwkby_id, connwkby.wkby, connwkby.wkid, " _
& "connwkby.projwkbyno, connwkby.projwkbynote, workby.workbytype " _
& "FROM workby INNER JOIN connwkby ON workby.workbyid = connwkby.wkby " _
& "WHERE (((connwkby.wkid)=" & mWkID & "))" _
& "ORDER BY connwkby.projwkbyno;"
'strSQL = "SELECT workby.wkid, workby.workbyid, workby.workbyno, workby.workbytype, workby.workbynote" _
& "FROM workby " _
& "ORDER BY workby.workbyno;"
Set rst = dbs.OpenRecordset(strSQL)
mReccount = rst.RecordCount
If mReccount = 3 Then
    Debug.Print "Got It!!!!!!!!!!!!!!!!!!!!!!!!!!"
End If
Debug.Print "FIRST RECCOUNT: " & mReccount
If mReccount = "" Then
    Debug.Print "********************Exiting for mrecount = ""!"""""""""""
    GoTo doaction:
End If
If IsNull(mReccount) = True Then
    Debug.Print "********************Exiting for mrecount = null!"""""""""""
    'printAction
    'Exit Sub
    GoTo doaction
End If
If mReccount = 1 Then
    With rst
        WRITEWORKBY = !workbytype
    End With
    GoTo doaction
End If
With rst
    ' Populate Recordset and print number of records.
    '.MoveLast
    '.MoveFirst
    Debug.Print "  Number of records - Workby = " & _
    .RecordCount
    'intRec = .RecordCount
    intRec = mReccount
    If intRec < 1 Then
        'Exit Sub
        GoTo doaction:
    End If
    If intRec = 1 Then
        tmpWorkby = !workbytype
        'Exit Sub
        Debug.Print "********************Exiting for mrecount = 1!"""""""""""
        WRITEWORKBY = tmpWorkby
        GoTo doaction:
    End If
    '.MoveFirst
    If intRec > 1 Then
        tmpWorkby = ""
        For x = 0 To intRec - 1
            tmpWorkby = tmpWorkby & !workbytype & "/"
            Debug.Print "Count i: and tmpWorkby: " & x & ": " & tmpWorkby & "<<<<<<<<<<-------"
            .MoveNext
        Next x
        nLen = Len(tmpWorkby)
        tmpWorkby = Mid(tmpWorkby, 1, nLen - 1)
        'Me.mWorkby = tmpWorkby
        WRITEWORKBY = tmpWorkby
        
    Else
        tmpWorkby = !workbytype
        nLen = Len(tmpWorkby)
        tmpWorkby = Mid(tmpWorkby, 1, nLen - 1)
        Debug.Print tmpWorkby
        'Me.mWorkby = tmpWorkby
         WRITEWORKBY = tmpWorkby
    End If
End With
doaction:
'printAction (mWkID)
rst.Close
Set dbs = Nothing

End Function
Function printAction(mWkID As Integer)


Dim ctl As Control
Dim varItm As Variant
Dim dbs As Database, rst As Object
Dim strSQL, tmpAction As String
    ' Return reference to current database.
Set dbs = OpenDatabase("\\jwja-svr-10\Jdb\db_est\X_EST_2013_001.mdb")
'DB_EST\X_EST_2013_001.mdb
    ' Open recordset on Employees table.
    'Set rst = dbs.OpenRecordset("ASSit", dbOpenDynaset)
Debug.Print mWkID
'strSQL = "SELECT connwkby.connwkby_id, connwkby.wkby, connwkby.wkid, connwkby.projwkbyno, connwkby.projwkbynote, workby.workbytype " _
& "FROM workby INNER JOIN connwkby ON workby.workbyid = connwkby.wkby " _
& "WHERE (((connwkby.wkid)=" & Me.WKID & "));"
strSQL = "SELECT connwkaction.connwkactionid, connwkaction.actionid, connwkaction.wkid, connwkaction.projwkactionno, workaction.wkaction " _
& "FROM workaction INNER JOIN connwkaction ON workaction.wkactionid = connwkaction.actionid " _
& "WHERE (((connwkaction.WKID) =" & mWkID & ")) " _
& "ORDER BY connwkaction.projwkactionno;"

'strSQL = "SELECT workby.wkid, workby.workbyid, workby.workbyno, workby.workbytype, workby.workbynote" _
& "FROM workby " _
& "ORDER BY workby.workbyno;"
Set rst = dbs.OpenRecordset(strSQL)
With rst
    ' Populate Recordset and print number of records.
    '.MoveLast
    '.MoveFirst
    Debug.Print "  Number of records = Work " & _
    .RecordCount
    intRec = .RecordCount
    If intRec < 1 Then
        rst.Close
        Set dbs = Nothing
        Debug.Print "********************Exiting for intRec < 1!!!!!!!!!!!!!!"
        Exit Function
    End If
    
    '.MoveFirst
    If intRec > 1 Then
        tmpAction = ""
        For x = 0 To intRec - 1
            tmpAction = tmpAction & !wkaction & "/"
            .MoveNext
        Next x
        mLen = Len(tmpAction)
        tmpAction = Mid(tmpAction, 1, mLen - 1)
    Else
        tmpAction = !wkaction
        'Me.mAction = tmpAction 'JIN TEST
        'rst.Close 'JIN TEST
        'Set dbs = Nothing 'JIN TEST
        Debug.Print "********************Exiting for intRec = 1:" & tmpAction & ">>>>>>>"
        Debug.Print tmpAction
    End If
End With
'Me.mAction = tmpAction
printAction = tmpAction
rst.Close
Set dbs = Nothing


End Function

Attribute VB_Name = "frmCode"
Attribute VB_Base = "0{4B043164-81D7-4ED1-85F5-E2FA9A44AB73}{C098D91A-4887-420F-B735-F142A4FA4AB2}"
Attribute VB_GlobalNameSpace = False
Attribute VB_Creatable = False
Attribute VB_PredeclaredId = True
Attribute VB_Exposed = False
Attribute VB_TemplateDerived = False
Attribute VB_Customizable = False

Public wksObj As Workspace
Public DB As Database
Public dbsObj As Database
Public tblObj As TableDef
Public fldObj As Field
Public rstObj, rstProj As Recordset

Private Sub CommandButton4_Click()

End Sub

Private Sub CommandButton8_Click()
writeRoom

End Sub

Public Sub UserForm_Initialize()
Dim DB As Database
Dim rstProj As Recordset
Dim strProj As String

' Define the workgroup information file (system database) you will use.
'DBEngine.SystemDB = "C:\Documents and Settings\Jinwoo\Application Data\Microsoft\Access\System6.mdw"
'DBEngine.SystemDB = "C:\Documents and Settings\jwjang\Application Data\Microsoft\Access\system.mdw"
DBEngine.SystemDB = "\\jwja-svr-10\jdb\JW0610.mdw"
' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")
'

'Set DB = OpenDatabase("H:\db\db_misc\cl_org_outspec_02.mdb")
Set DB = OpenDatabase("\\jwja-svr-10\jdb\db_outspec\X-CL_ORG_OUTSPEC_02.mdb")

'X-CL_ORG_OUTSPEC_02
'Set DB = OpenDatabase("X:\db_misc\02_Jspec_B_001.mdb")
'Set DB = OpenDatabase("h:\db\db_misc\JSPEC0310.mdb")

'Set Rs = DB.OpenRecordset("project")

'strPCSI = "SELECT PROJSPEC.PROJSPECID, PROJSPEC.PROJ_NO, PROJSPEC.NOTE, " _
& "PROJSPEC.PROJSPECDATE, PROJSPEC.NOTE, Project.PROJ_NAME " _
& "FROM PROJSPEC INNER JOIN Project ON PROJSPEC.PROJ_NO = Project.PROJ_NO " _
& "ORDER BY PROJSPEC.PROJ_NO"

strProj = "SELECT projcode.projcodeid, PROJCODE.PROJ_NO, Project.PROJ_NAME " _
& "FROM Project INNER JOIN PROJCODE ON Project.PROJ_NO = PROJCODE.PROJ_NO " _
& "ORDER BY Project.INPUT DESC"



Set rstProj = DB.OpenRecordset(strProj)

Do Until rstProj.EOF = True
    seleproj.AddItem rstProj!projcodeid
    seleproj.List(seleproj.ListCount - 1, 1) = rstProj!PROJ_NO
    seleproj.List(seleproj.ListCount - 1, 2) = rstProj!PROJ_NAME
    rstProj.MoveNext
Loop
rstProj.Close
Set rstProj = Nothing
DB.Close
Set DB = Nothing

' OPTIONAL: If you set the WS object, use the following to clean up
'WS.Close
'Set WS = Nothing

MsgBox "Project List for Code LOADED!"


End Sub

Private Sub CommandButton3_Click()
Unload Me
End Sub

Private Sub CommandButton7_Click()
Dim x As Integer
'If IsNull(ListBox1) = True Then
'If ListBox1.Selected(1) = False Then
'MsgBox "Must select a Assembly Item from the list!"
'Exit Sub
'Else
'x = ListBox1
x = showARDU
writeCode (x)
'frmWorkItem.HIDE
'End If

End Sub



Private Sub seleproj_Change()
'frmCode.Repaint
'CommandButton4_Click 'POPULATE CSI
Debug.Print seleproj
End Sub

Attribute VB_Name = "frmDoor"
Attribute VB_Base = "0{407619B4-6148-4ECD-8A7B-26A24B41FE1B}{439F437B-234B-4D80-B95B-B0378E40C6DB}"
Attribute VB_GlobalNameSpace = False
Attribute VB_Creatable = False
Attribute VB_PredeclaredId = True
Attribute VB_Exposed = False
Attribute VB_TemplateDerived = False
Attribute VB_Customizable = False

Public WS As Workspace
Public DB As Database
Public dbsObj As Database
Public tblObj As TableDef
Public fldObj As Field
Public rstObj, rstProj As Recordset


Private Sub CommandButton8_Click()
writeRoom
End Sub



Public Sub UserForm_Initialize()
Dim WS As Workspace
Dim DB As Database
Dim RsPDR, RsPPT As Recordset
Dim strPDR, strPPT As String

' Define the workgroup information file (system database) you will use.
'DBEngine.SystemDB = "C:\Documents and Settings\Jinwoo\Application Data\Microsoft\Access\System6.mdw"
'DBEngine.SystemDB = "C:\Documents and Settings\jwjang\Application Data\Microsoft\Access\SECURED.mdw"
'DBEngine.SystemDB = "C:\Documents and Settings\JINWOO\Application Data\Microsoft\Access\SECURED.mdw"
'DBEngine.SystemDB = "C:\Documents and Settings\jwjang\Application Data\Microsoft\Access\system.mdw"
' 062010 AT UPSTAIR SYSTEM7.MDW
'DBEngine.SystemDB = "H:\DB\JW0610.mdw"

DBEngine.SystemDB = "\\jwja-svr-10\jdb\JW0610.mdw"

' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")

'**********************************************************
'Set DB = OpenDatabase("h:\db\db_misc\Door02_01.mdb")
'**********************************************************
'**********************************************************
Set DB = OpenDatabase("\\jwja-svr-10\jdb\db_misc\Door02_01.mdb")
'**********************************************************


'Set DB = OpenDatabase("h:\db\DATAS\DT11_JPM_01.mdb")

'Set Rs = DB.OpenRecordset("project")

'strPDR = "SELECT Project.PROJ_NO, Project.PROJ_NAME, Project.STATUS, Project.INPUT " _
& "FROM DRGP INNER JOIN Project ON DRGP.PROJ_NO = Project.PROJ_NO " _
& "GROUP BY Project.PROJ_NO, Project.PROJ_NAME, Project.STATUS, Project.INPUT " _
& "HAVING (((Project.Status) = 'act'))" _
& "ORDER BY Project.INPUT DESC;"

strPDR = "SELECT Project.PROJ_NO, Project.PROJ_NAME, Project.STATUS, Project.INPUT " _
& "FROM Project  " _
& "GROUP BY Project.PROJ_NO, Project.PROJ_NAME, Project.STATUS, Project.INPUT " _
& "HAVING (((Project.Status) = 'act'))" _
& "ORDER BY Project.INPUT DESC;"

Set RsPDR = DB.OpenRecordset(strPDR)
Do Until RsPDR.EOF = True
    seleproj.AddItem RsPDR!PROJ_NO
    seleproj.List(seleproj.ListCount - 1, 1) = RsPDR!PROJ_NAME
    RsPDR.MoveNext
Loop
RsPDR.Close
Set RsPPT = Nothing
DB.Close
Set DB = Nothing
'**********************************************************
'**********************************************************
'**********************************************************

'**********************************************************
'Set DB = OpenDatabase("h:\db\db_misc\Partition.mdb")
'**********************************************************

'**********************************************************
Set DB = OpenDatabase("\\jwja-svr-10\jdb\db_misc\Partition.mdb")
'**********************************************************



strPPT = "SELECT Project.PROJ_NO, Project.PROJ_NAME, Project.STATUS, Project.INPUT " _
& "FROM ProPart INNER JOIN Project ON ProPart.PROJ_NO = Project.PROJ_NO " _
& "GROUP BY Project.PROJ_NO, Project.PROJ_NAME, Project.STATUS, Project.INPUT " _
& "HAVING (((Project.Status) = 'act'))" _
& "ORDER BY Project.INPUT DESC;"
Set RsPPT = DB.OpenRecordset(strPPT)
Do Until RsPPT.EOF = True
    seleprojpart.AddItem RsPPT!PROJ_NO
    seleprojpart.List(seleprojpart.ListCount - 1, 1) = RsPPT!PROJ_NAME
    RsPPT.MoveNext
Loop
RsPPT.Close
Set RsPPT = Nothing
DB.Close
Set DB = Nothing

'**********************************************************
'**********************************************************
'**********************************************************



' OPTIONAL: If you set the WS object, use the following to clean up
'WS.Close
'Set WS = Nothing

MsgBox "Projects Loaded!"
frmDoor.Hide
End Sub
Private Sub CommandButton1_Click()
Unload Me
End Sub

Private Sub CommandButton2_Click()
mkDr
End Sub

Private Sub Example()
' Define the block
Dim blockObj As AcadBlock
Dim insertionPnt(0 To 2) As Double
insertionPnt(0) = 0
insertionPnt(1) = 0
insertionPnt(2) = 0
Set blockObj = ThisDrawing.Blocks.Add _
          (insertionPnt, "BlockWithAttribute")

' Add an attribute to the block
Dim attributeObj As AcadAttribute
Dim height As Double
Dim mode As Long
Dim prompt As String
Dim insertionPoint(0 To 2) As Double
Dim tag As String
Dim value As String
height = 1
mode = acAttributeModeVerify
prompt = "New Prompt"
insertionPoint(0) = 5
insertionPoint(1) = 5
insertionPoint(2) = 0
tag = "New Tag"
value = "New Value"
Set attributeObj = blockObj.AddAttribute(height, mode, _
               prompt, insertionPoint, tag, value)
' Insert the block, creating a block reference
' and an attribute reference
Dim blockRefObj As AcadBlockReference
insertionPnt(0) = 2
insertionPnt(1) = 2
insertionPnt(2) = 0
Set blockRefObj = ThisDrawing.ModelSpace.InsertBlock _
    (insertionPnt, "BlockWithAttribute", 1#, 1#, 1#, 0)

End Sub


Private Sub CommandButton3_Click()
MkHDWRimg
End Sub

Private Sub CommandButton4_Click()
Partition
End Sub




Private Sub CommandButton5_Click()
If Me.writeDoor = True Then
    mkDr
ElseIf Me.writeWindow = True Then
    writeWinImg
End If

End Sub

Private Sub ListBox2_Click()
Dim DB As Database
Dim RsProjWinItem As Recordset
Dim strProjWinItem As String
Dim rn As Integer
Dim rcArray As Variant
ListBox1.Clear

'**********************************************************
'Set DB = OpenDatabase("h:\db\db_misc\Door02_01.mdb")
'**********************************************************
'**********************************************************
Set DB = OpenDatabase("\\jwja-svr-10\jdb\db_misc\Door02_01.mdb")
'**********************************************************



strProjWinItem = "SELECT projwin.projwinid, connprojwin.connprojwinid, connprojwin.projwinno, " _
& "WINDOW.WINSIZE, WINDOW.CATNO, WINDOW.WINMAT, WINDOW.WINTYPE, WINDOW.WINMODEL, WINDOW.WINAREA, " _
& "WINDOW.WINOPENAREA, WINDOW.WINIMGNAME " _
& "FROM (projwin INNER JOIN connprojwin ON projwin.projwinid = connprojwin.projwinid) " _
& "INNER JOIN WINDOW ON connprojwin.winid = WINDOW.WINID " _
& "WHERE (((projwin.projwinid)=" & ListBox2 & ")) " _
& "ORDER BY connprojwin.PROJWINNO;"
Set RsProjWinItem = DB.OpenRecordset(strProjWinItem)
rn = RsProjWinItem.RecordCount
Debug.Print rn
Do Until RsProjWinItem.EOF = True
    ListBox1.AddItem RsProjWinItem!projwinid
    ListBox1.List(ListBox1.ListCount - 1, 1) = RsProjWinItem!projwinid
    'ListBox1.List(ListBox1.ListCount - 1, 2) = RsDRG!DRGNOTE
    RsProjWinItem.MoveNext
Loop

End Sub

Private Sub seleproj_Change()
frmDoor.Repaint
Dim DB As Database
Dim RsDRG As Recordset
Dim strDRG As String
Dim rn As Integer
Dim rcArray As Variant
ListBox1.Clear
'**********************************************************
'Set DB = OpenDatabase("h:\db\db_misc\Door02_01.mdb")
'**********************************************************
'**********************************************************
Set DB = OpenDatabase("\\jwja-svr-10\jdb\db_misc\Door02_01.mdb")
'**********************************************************


If Me.writeDoor = True Then

    strDRG = "SELECT DRGP.DRGID, DRGP.DRID, DRGP.PROJ_NO, DRGP.DRGNO, DRGP.DRTYPE, " _
    & "DRGP.DRFIN, DRGP.DRFRAME, DRGP.DRJAMB, DRGP.DRHEAD, DRGP.HDSET, DRGP.DRGNOTE, " _
    & "DR.DRWIDTH, DR.DRHEIGHT, DR.DRMAT, DR.DRTHK, DR.DRMFGR, DR.DRFIRE, DR.DRNOTE, DR.OLDSIZE " _
    & "FROM DRGP INNER JOIN DR ON DRGP.DRID = DR.DRID " _
    & "WHERE (((DRGP.PROJ_NO) = '" & seleproj & "')) " _
    & "ORDER BY DRGP.DRGNO;"
    Set RsDRG = DB.OpenRecordset(strDRG)
    Debug.Print rn
    Do Until RsDRG.EOF = True
        ListBox1.AddItem RsDRG!DRGNO
        ListBox1.List(ListBox1.ListCount - 1, 1) = RsDRG!OLDSIZE
        'ListBox1.List(ListBox1.ListCount - 1, 2) = RsDRG!DRGNOTE
        RsDRG.MoveNext
    Loop
ElseIf Me.writeWindow = True Then
    strProjWin = "SELECT projwin.projwinid, projwin.proj_no, projwin.connprojwin, projwin.note, projwin.input " _
    & "FROM projwin " _
    & "WHERE (((projwin.proj_no) = '" & seleproj & "')) " _
    & "ORDER BY projwin.projwinid;"
    Set RsProjWin = DB.OpenRecordset(strProjWin)
    Debug.Print rn
    Do Until RsProjWin.EOF = True
        ListBox2.AddItem RsProjWin!projwinid
        ListBox2.List(ListBox2.ListCount - 1, 1) = RsProjWin!PROJ_NO
        'ListBox1.List(ListBox1.ListCount - 1, 2) = RsDRG!DRGNOTE
        RsProjWin.MoveNext
    Loop

End If

End Sub
Sub Partition()

Dim DB As Database
Dim RstParti As Recordset
Dim strParti, txtRow As String
Dim rnParti As Integer   'ProjSet no.
Dim TblPT(0 To 2) As Double
Dim tblPT2(0 To 2) As Double
Dim tblWidth As Double
Dim txtHt As Double
Dim textObj As AcadText
Dim attributeObj As AcadAttribute
Dim height As Double
Dim mode As Long
Dim prompt, mKey As String
Dim blockRefObj As AcadBlockReference
Dim BlkObj As Object
Dim i, iat As Integer

'frmDoor.ListBox1.Clear
'**********************************************************
'Set DB = OpenDatabase("h:\db\db_misc\partition.mdb")
'**********************************************************

'**********************************************************
Set DB = OpenDatabase("\\jwja-svr-10\jdb\db_misc\partition.mdb")
'**********************************************************


strParti = "SELECT PROPART.PRPTID, PROPART.KEY, PROPART.EXTENT, PROPART.FIGURE, " _
& "PROPART.NOTE, PARTITION.THK, PARTITION.FIRE, PARTITION.INSUL, PARTITION.STC, PARTITION.TestNo, " _
& "PARTITION.PTNOTE, Sub.SubDepth, Sub.SubTYPE, CONNLayer.PTID, CONNLayer.SIDE, Layer.LayerTHK, " _
& "Layer.LayerTYPE, PROPART.PROJ_NO " _
& "FROM Sub INNER JOIN ((PARTITION INNER JOIN (Layer INNER JOIN CONNLayer ON Layer.LayerID = CONNLayer.LayerID) " _
& "ON PARTITION.PTID = CONNLayer.PTID) INNER JOIN PROPART ON PARTITION.PTID = PROPART.PTID) ON Sub.SubID = PARTITION.SubID " _
& "GROUP BY PROPART.PRPTID, PROPART.KEY, PROPART.EXTENT, PROPART.FIGURE, PROPART.NOTE, PARTITION.THK, PARTITION.FIRE, " _
& "PARTITION.INSUL, PARTITION.STC, PARTITION.TestNo, PARTITION.PTNOTE, Sub.SubDepth, Sub.SubTYPE, " _
& "CONNLayer.PTID, CONNLayer.SIDE, Layer.LayerTHK, Layer.LayerTYPE, PROPART.PROJ_NO " _
& "HAVING (((PROPART.PROJ_NO)='" & seleprojpart & "')) " _
& "ORDER BY PROPART.KEY;"

RecordSets:
Set RstParti = DB.OpenRecordset(strParti, dbOpenDynaset)

If RstParti.RecordCount = 0 Then
    GoTo ExitPartition
End If

TblPT(0) = 0: TblPT(1) = 0: TblPT(2) = 0
tblPT2(0) = -300: tblPT2(1) = 0: tblPT2(2) = 0
txtHt = 4
txtRow = ""
mode = acAttributeModeVerify
'InsertJBlock "e:\drawfile\jvba\XHDWRHEAD01.dwg", tblPT, "Model"

'**********************************************************************************************
'ThisDrawing.ModelSpace.InsertBlock tblPT, "H:\drawfile\jvba\XPARTIHEAD01.dwg", 1, 1, 1, 0
'**********************************************************************************************

'**********************************************************************************************
ThisDrawing.ModelSpace.InsertBlock TblPT, "\\jwja-svr-10\drawfile\jvba\XPARTIHEAD01.dwg", 1, 1, 1, 0
'**********************************************************************************************
'**********************************************************************************************
'InsertJBlock "H:\drawfile\jvba\XPARTIROW01.dwg", tblPT2, "Model"
'**********************************************************************************************
'**********************************************************************************************
InsertJBlock "\\jwja-svr-10\drawfile\jvba\XPARTIROW01.dwg", tblPT2, "Model"
'**********************************************************************************************



TblPT(1) = TblPT(1) - 48
RstParti.MoveLast
RstParti.MoveFirst
rnParti = RstParti.RecordCount
Debug.Print rnParti

With RstParti
    For i = 1 To rnParti
    If !Key = mKey Then
    GoTo PARTINEXT
    End If
         Set blockRefObj = ThisDrawing.ModelSpace.InsertBlock _
                     (TblPT, "XPARTIROW01", 1, 1, 1, 0)
        '******************************
          'Get the block's attributes
                Dim varAttributes As Variant
                varAttributes = blockRefObj.GetAttributes
                    For iat = LBound(varAttributes) To UBound(varAttributes)
                    Debug.Print varAttributes(iat).TagString
                        If varAttributes(iat).TagString = "XKEY" Then
                            If IsNull(!Key) = True Then
                                varAttributes(iat).textString = ""
                            Else
                                varAttributes(iat).textString = !Key
                                Debug.Print varAttributes(iat).textString
                            End If
                        End If
                        If varAttributes(iat).TagString = "XDEPTH" Then
                            If IsNull(!THK) = True Then
                                varAttributes(iat).textString = ""
                            Else
                                varAttributes(iat).textString = Num2Frac(!THK) & """"
                                Debug.Print varAttributes(iat).textString
                            End If
                        End If
                        If varAttributes(iat).TagString = "XSUBDEPTH" Then
                            If IsNull(!SUBDEPTH) = True Then
                                varAttributes(iat).textString = ""
                            Else
                                varAttributes(iat).textString = Num2Frac(!SUBDEPTH) & """"
                                Debug.Print varAttributes(iat).textString
                            End If
                        End If
                        If varAttributes(iat).TagString = "XSUBTYPE" Then
                            If IsNull(!SUBTYPE) = True Then
                                varAttributes(iat).textString = ""
                            Else
                                varAttributes(iat).textString = !SUBTYPE
                                Debug.Print varAttributes(iat).textString
                            End If
                        End If
                        If varAttributes(iat).TagString = "XLAYERTHK" Then
                            If IsNull(!LAYERTHK) = True Then
                                varAttributes(iat).textString = ""
                            Else
                                varAttributes(iat).textString = Num2Frac(!LAYERTHK) & """"
                                Debug.Print varAttributes(iat).textString
                            End If
                        End If
                        If varAttributes(iat).TagString = "XFIRE" Then
                            If IsNull(!FIRE) = True Then
                                varAttributes(iat).textString = ""
                            Else
                                varAttributes(iat).textString = !FIRE
                                Debug.Print varAttributes(iat).textString
                            End If
                        End If
                        If varAttributes(iat).TagString = "XINSUL" Then
                            If IsNull(!INSUL) = True Then
                                varAttributes(iat).textString = ""
                            Else
                                varAttributes(iat).textString = !INSUL
                                Debug.Print varAttributes(iat).textString
                            End If
                        End If
                        If varAttributes(iat).TagString = "XSTC" Then
                            If IsNull(!STC) = True Then
                                varAttributes(iat).textString = ""
                            Else
                                varAttributes(iat).textString = !STC
                                Debug.Print varAttributes(iat).textString
                            End If
                        End If
                        If varAttributes(iat).TagString = "XTESTNO" Then
                            If IsNull(!TestNo) = True Then
                                varAttributes(iat).textString = ""
                            Else
                             '********** pre 2014 **********
                             '   If Len(!testno) > 7 Then
                             '   varAttributes(iat).TextString = Left(!testno, 6)
                                
                             '   TestNo2 = Mid(!testno, 7, Len(!testno))
                             '   Else
                             '   varAttributes(iat).TextString = !testno
                             '   End If
                             varAttributes(iat).textString = SEPTEXT2(!TestNo, 1, 2, 6)
                                Debug.Print varAttributes(iat).textString
                            End If
                        End If
                        If varAttributes(iat).TagString = "XTESTNO2" Then
                            If IsNull(!TestNo) = True Then
                                varAttributes(iat).textString = ""
                            Else
                                'varAttributes(iat).TextString = Trim(TestNo2)
                                varAttributes(iat).textString = SEPTEXT2(!TestNo, 2, 2, 6)
                                Debug.Print varAttributes(iat).textString
                            End If
                        End If

                        If varAttributes(iat).TagString = "XEXTENT" Then
                            If IsNull(!EXTENT) = True Then
                                varAttributes(iat).textString = ""
                            Else
                                varAttributes(iat).textString = !EXTENT
                                Debug.Print varAttributes(iat).textString
                            End If
                        End If
                        If varAttributes(iat).TagString = "XFIGURE" Then
                            If IsNull(!FIGURE) = True Then
                                varAttributes(iat).textString = ""
                            Else
                                varAttributes(iat).textString = !FIGURE
                                Debug.Print varAttributes(iat).textString
                            End If
                        End If
                        If varAttributes(iat).TagString = "XNOTE" Then
                            If IsNull(!NOTE) = True Then
                                varAttributes(iat).textString = ""
                            Else
                            '********** pre 2014 **********
                            '    If Len(!NOTE) > 20 Then
                            '        varAttributes(iat).TextString = Left(!NOTE, 19)
                                
                            '        Note2 = Mid(!NOTE, 20, Len(!NOTE))
                            '    Else
                            '        varAttributes(iat).TextString = !NOTE
                            '    Debug.Print varAttributes(iat).TextString
                            '    End If
                            '********** pre 2014 **********
                                varAttributes(iat).textString = SEPTEXT2(!NOTE, 1, 2, 22)
                            End If
                        End If
                        If varAttributes(iat).TagString = "XNOTE2" Then
                            If IsNull(!NOTE) = True Then
                                varAttributes(iat).textString = ""
                            Else
                                'varAttributes(iat).TextString = Note2
                                varAttributes(iat).textString = SEPTEXT2(!NOTE, 2, 2, 22)
                                Debug.Print varAttributes(iat).textString
                            End If
                        End If
                        
                    Next iat
                    mKey = !Key
        TblPT(1) = TblPT(1) - 20
PARTINEXT:
        .MoveNext
    Next i
End With
'Set blockRefObj = ThisDrawing.ModelSpace.InsertBlock _
                                             (tblPT, "XHDWRFOOT02", 1, 1, 1, 0)
RstParti.Close
Set DB = Nothing
ExitPartition:
frmDoor.Hide

End Sub

Private Sub WindSchType_Click()

End Sub

Private Sub writeWindow_Click()
seleproj_Change
End Sub

Attribute VB_Name = "frmInsp"
Attribute VB_Base = "0{DAEE92D1-B3A9-406F-81C7-C1B67CA02551}{0A5A5A91-A60F-49EC-8960-11D323A8FBB7}"
Attribute VB_GlobalNameSpace = False
Attribute VB_Creatable = False
Attribute VB_PredeclaredId = True
Attribute VB_Exposed = False
Attribute VB_TemplateDerived = False
Attribute VB_Customizable = False
Private Sub CheckBox1_Click()

End Sub

Private Sub CommandButton10_Click()
writeEnergyTabularNW
End Sub

Private Sub CommandButton8_Click()

Dim x As Integer
'If IsNull(ListBox1) = True Then
'If ListBox1.Selected(1) = False Then
'MsgBox "Must select a Assembly Item from the list!"
'Exit Sub
'Else
'x = ListBox1
writeEnergyInsp
'frmWorkItem.HIDE
'End If


End Sub

Private Sub CommandButton9_Click()
'writeEnergyTabular
writeEnergyTabularXT
End Sub

Private Sub seleProjECC_Change()
EnergyList
End Sub



Public Sub UserForm_Initialize()
Dim DB As Database
Dim rstProj As Recordset
Dim strProj As String

' Define the workgroup information file (system database) you will use.
'DBEngine.SystemDB = "C:\Documents and Settings\Jinwoo\Application Data\Microsoft\Access\System6.mdw"
'DBEngine.SystemDB = "C:\Documents and Settings\jwjang\Application Data\Microsoft\Access\system.mdw"
'DBEngine.SystemDB = "H:\DB\JW0610.mdw"
DBEngine.SystemDB = "\\jwja-svr-10\jdb\JW0610.mdw"

' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")
'
'Set DB = OpenDatabase("H:\db\db_misc\dob_inspections_01.mdb")
Set DB = OpenDatabase("\\jwja-svr-10\jdb\db_DOB_INSPECTIONS\X-dob_inspections_02.mdb")
'Set DB = OpenDatabase("X:\db_misc\02_Jspec_B_001.mdb")
'Set DB = OpenDatabase("h:\db\db_misc\JSPEC0310.mdb")

'Set Rs = DB.OpenRecordset("project")

'strPCSI = "SELECT PROJSPEC.PROJSPECID, PROJSPEC.PROJ_NO, PROJSPEC.NOTE, " _
& "PROJSPEC.PROJSPECDATE, PROJSPEC.NOTE, Project.PROJ_NAME " _
& "FROM PROJSPEC INNER JOIN Project ON PROJSPEC.PROJ_NO = Project.PROJ_NO " _
& "ORDER BY PROJSPEC.PROJ_NO"

'strProj = "SELECT projcode.projcodeid, PROJCODE.PROJ_NO, Project.PROJ_NAME " _
& "FROM Project INNER JOIN PROJCODE ON Project.PROJ_NO = PROJCODE.PROJ_NO " _
& "ORDER BY Project.INPUT DESC"

strProj = "SELECT PROJINSP.PROJINSPID, PROJINSP.PROJ_NO, PROJINSP.INPUT, PROJINSP.NOTE, " _
& "PROJINSP.REMARK, PROJINSP.CID, Project.PROJ_NAME, Project.PROJ_STNO, Project.PROJ_ADDR, " _
& "Project.PROJ_CITY, Project.PROJ_STATE, Project.PROJ_ZIP, Project.BIS " _
& "FROM Project INNER JOIN PROJINSP ON Project.PROJ_NO = PROJINSP.PROJ_NO " _
& "ORDER BY PROJINSP.INPUT desc;"

Set rstProj = DB.OpenRecordset(strProj)

Do Until rstProj.EOF = True
    seleproj.AddItem rstProj!PROJinspID
    seleproj.List(seleproj.ListCount - 1, 1) = rstProj!PROJ_NO
    seleproj.List(seleproj.ListCount - 1, 2) = rstProj!PROJ_NAME
    'seleproj.List(seleproj.ListCount - 1, 2) = rstProj!NOTE
    rstProj.MoveNext
Loop
rstProj.Close
Set rstProj = Nothing
DB.Close
Set DB = Nothing

' OPTIONAL: If you set the WS object, use the following to clean up
'WS.Close
'Set WS = Nothing

MsgBox "Project List for Inspection LOADED!"


End Sub

Private Sub CommandButton3_Click()
Unload Me
End Sub

Private Sub CommandButton7_Click()
Dim x As Integer
'If IsNull(ListBox1) = True Then
'If ListBox1.Selected(1) = False Then
'MsgBox "Must select a Assembly Item from the list!"
'Exit Sub
'Else
'x = ListBox1
writeInsp
'frmWorkItem.HIDE
'End If

End Sub



Private Sub seleproj_Change()
'frmCode.Repaint
CommandButton4_Click 'POPULATE CSI
Debug.Print seleproj
End Sub

Public Sub CommandButton4_Click() 'Test Populate CSI
Dim rstProjInsp As Recordset
Dim strProjInsp As String
Dim DB As Database
Dim rn As Integer
Dim rcArray As Variant
ListBox1.Clear
ListBox1.MultiSelect = fmMultiSelectExtended
'Set DB = OpenDatabase("h:\db\db_misc\JSPEC0310.mdb")
'Set DB = OpenDatabase("h:\db\db_misc\02_Jspec_B_001.mdb")
'Set DB = OpenDatabase("X:\db_misc\02_Jspec_B_001.mdb")
'Set DB = OpenDatabase("H:\db\db_misc\JSPEC04_01.mdb")
'Set DB = OpenDatabase("H:\db\db_est\H_H_EST_2012_001.mdb")
Set DB = OpenDatabase("\\jwja-svr-10\jdb\db_DOB_INSPECTIONS\X-dob_inspections_02.mdb")
'strPCSI2 = "SELECT PROJCSI.projcsiid, PROJCSI.PROJ_NO, MCSI.MCSI, MCSI.MCSINAME " _
& "FROM MCSI INNER JOIN PROJCSI ON MCSI.MCSIID = PROJCSI.MCSIID " _
& "WHERE (((PROJCSI.PROJ_NO) = '" & seleproj & "'))" _
& "ORDER BY MCSI.MCSI"

'strProjAss = "SELECT ASS.ASSID, ASS.ESTID, ASS.ASSDIV, ASS.ASSNO, ASS.ASSSUBDIV, ASS.ASSNAME, ASS.proj_no " _
& "FROM ASS " _
& "WHERE (((ASS.proj_no) = '" & seleproj & "'))" _
& "ORDER BY ASS.ASSDIV, ASS.ASSNO"

strProjInsp = "SELECT PROJINSPITEM.proj_no, PROJINSPITEM.projinspid, PROJINSPITEM.INPUT, " _
& "INSPECTION.INSPTYPE, INSPECTION.CODENO, INSPECTION.INSPNAME " _
& "FROM INSPECTION INNER JOIN PROJINSPITEM ON INSPECTION.INSPID = PROJINSPITEM.INSPID " _
& "WHERE (((PROJINSPITEM.projinspid) = " & seleproj & ")) " _
& "ORDER BY INSPECTION.INSPTYPE, INSPECTION.INSPID;"



Set rstProjInsp = DB.OpenRecordset(strProjInsp)
Debug.Print rn
Do Until rstProjInsp.EOF = True
    ListBox1.AddItem rstProjInsp!PROJinspID
    ListBox1.List(ListBox1.ListCount - 1, 1) = rstProjInsp!input
    ListBox1.List(ListBox1.ListCount - 1, 2) = rstProjInsp!INSPTYPE
    ListBox1.List(ListBox1.ListCount - 1, 3) = rstProjInsp!INSPNAME
    rstProjInsp.MoveNext
Loop
rstProjInsp.Close
Set rstProjInsp = Nothing
DB.Close
Set DB = Nothing
PopulateEnergyCombo
'EnergyList
End Sub
Public Sub PopulateEnergyCombo() 'Populate Energy ComboBox
Dim DB As Database
Dim rstProjECCList As Recordset
Dim strProjECCList As String

' Define the workgroup information file (system database) you will use.
'DBEngine.SystemDB = "H:\DB\JW0610.mdw"
DBEngine.SystemDB = "\\jwja-svr-10\jdb\JW0610.mdw"

' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")
'
'Set DB = OpenDatabase("H:\db\db_misc\dob_inspections_01.mdb")
Set DB = OpenDatabase("\\jwja-svr-10\jdb\db_DOB_INSPECTIONS\X-dob_inspections_02.mdb")
'Set DB = OpenDatabase("X:\db_misc\02_Jspec_B_001.mdb")
'Set DB = OpenDatabase("h:\db\db_misc\JSPEC0310.mdb")


'strProj = "SELECT projcode.projcodeid, PROJCODE.PROJ_NO, Project.PROJ_NAME " _
& "FROM Project INNER JOIN PROJCODE ON Project.PROJ_NO = PROJCODE.PROJ_NO " _
& "ORDER BY Project.INPUT DESC"

'strProj = "SELECT PROJINSP.PROJINSPID, PROJINSP.PROJ_NO, PROJINSP.INPUT, PROJINSP.NOTE, " _
& "PROJINSP.REMARK, PROJINSP.CID, Project.PROJ_NAME, Project.PROJ_STNO, Project.PROJ_ADDR, " _
& "Project.PROJ_CITY, Project.PROJ_STATE, Project.PROJ_ZIP, Project.BIS " _
& "FROM Project INNER JOIN PROJINSP ON Project.PROJ_NO = PROJINSP.PROJ_NO;"
strProjECCList = "SELECT PROJECC.projeccid, PROJECC.note, PROJECC.proj_no " _
& "FROM PROJECC " _
& "WHERE (((PROJECC.proj_no)='" & seleproj.Column(1) & "'));"

Set rstProjECCList = DB.OpenRecordset(strProjECCList)

Do Until rstProjECCList.EOF = True
    seleProjECC.AddItem rstProjECCList!projeccid
    seleProjECC.List(seleProjECC.ListCount - 1, 1) = rstProjECCList!PROJ_NO
    seleProjECC.List(seleProjECC.ListCount - 1, 2) = rstProjECCList!NOTE
    'seleproj.List(seleproj.ListCount - 1, 2) = rstProj!NOTE
    rstProjECCList.MoveNext
Loop
rstProjECCList.Close
Set rstProjECCList = Nothing
DB.Close
Set DB = Nothing

' OPTIONAL: If you set the WS object, use the following to clean up
'WS.Close
'Set WS = Nothing

MsgBox "Project ECC List for Project LOADED!"


End Sub


Public Sub EnergyList() 'Populate Energy ListBox
Dim rstProjECC As Recordset
Dim strProjECC As String
Dim DB As Database
Dim rn As Integer
Dim rcArray As Variant
ListBox2.Clear
ListBox2.MultiSelect = fmMultiSelectExtended
'Set DB = OpenDatabase("h:\db\db_misc\JSPEC0310.mdb")
'Set DB = OpenDatabase("h:\db\db_misc\02_Jspec_B_001.mdb")
'Set DB = OpenDatabase("X:\db_misc\02_Jspec_B_001.mdb")
'Set DB = OpenDatabase("H:\db\db_misc\JSPEC04_01.mdb")
'Set DB = OpenDatabase("H:\db\db_est\H_H_EST_2012_001.mdb")
Set DB = OpenDatabase("\\jwja-svr-10\jdb\db_DOB_INSPECTIONS\X-dob_inspections_02.mdb")
'strPCSI2 = "SELECT PROJCSI.projcsiid, PROJCSI.PROJ_NO, MCSI.MCSI, MCSI.MCSINAME " _
& "FROM MCSI INNER JOIN PROJCSI ON MCSI.MCSIID = PROJCSI.MCSIID " _
& "WHERE (((PROJCSI.PROJ_NO) = '" & seleproj & "'))" _
& "ORDER BY MCSI.MCSI"

'strProjAss = "SELECT ASS.ASSID, ASS.ESTID, ASS.ASSDIV, ASS.ASSNO, ASS.ASSSUBDIV, ASS.ASSNAME, ASS.proj_no " _
& "FROM ASS " _
& "WHERE (((ASS.proj_no) = '" & seleproj & "'))" _
& "ORDER BY ASS.ASSDIV, ASS.ASSNO"

'strProjInsp = "SELECT PROJINSPITEM.proj_no, PROJINSPITEM.projinspid, PROJINSPITEM.INPUT, " _
& "INSPECTION.INSPTYPE, INSPECTION.CODENO, INSPECTION.INSPNAME " _
& "FROM INSPECTION INNER JOIN PROJINSPITEM ON INSPECTION.INSPID = PROJINSPITEM.INSPID " _
& "WHERE (((PROJINSPITEM.projinspid) = " & seleproj & ")) " _
& "ORDER BY INSPECTION.INSPTYPE, INSPECTION.INSPID;"

strProjECC = "SELECT PROJECC.projeccid, PROJECCITEM.projeccitemid, " _
& "PROJECCITEM.ecctabid, ECC.citation, ECC.provision, PROJECCITEM.projeccdesc, " _
& "PROJECC.proj_no " _
& "FROM (PROJECC INNER JOIN PROJECCITEM ON PROJECC.projeccid = PROJECCITEM.projeccid) " _
& "INNER JOIN ECC ON PROJECCITEM.ecctabid = ECC.ecctabid " _
& "WHERE (((PROJECC.proj_no)='" & seleproj.Column(1) & "')) " _
& "ORDER BY ECC.citation;"


Set rstProjECC = DB.OpenRecordset(strProjECC)
Debug.Print rn
Do Until rstProjECC.EOF = True
    ListBox2.AddItem rstProjECC!PROJ_NO
    ListBox2.List(ListBox2.ListCount - 1, 1) = rstProjECC!citation
    ListBox2.List(ListBox2.ListCount - 1, 2) = rstProjECC!provision
    ListBox2.List(ListBox2.ListCount - 1, 3) = rstProjECC!projeccdesc
    rstProjECC.MoveNext
Loop
rstProjECC.Close
Set rstProjECC = Nothing
DB.Close
Set DB = Nothing
End Sub

Attribute VB_Name = "frmProjCode"
Attribute VB_Base = "0{F8300712-82AE-4329-BC51-4090053B1597}{C131A017-8B0F-4677-ADDA-21D7763868C0}"
Attribute VB_GlobalNameSpace = False
Attribute VB_Creatable = False
Attribute VB_PredeclaredId = True
Attribute VB_Exposed = False
Attribute VB_TemplateDerived = False
Attribute VB_Customizable = False
'==========================================================================================================

Private Sub cmdWriteProjCode_Click()
Dim x As Integer
If IsNull(listseleCode) = True Then
    MsgBox "Must select a Chapter from the list!"
    Exit Sub
Else
    x = listseleCode
    mprojcodeID = seleproj
    y = writeProjCode(mprojcodeID, x) '<<<<<<<<<<<<<<<<<<<<<<<<<<<<<<<<<<<<<<<<<<<<<<<<<<<<<<<<<
    frmProjCode.Hide
End If

End Sub

Private Sub cmdWriteProjCodeNW_Click()
Dim x As Integer
If IsNull(listseleCode) = True Then
    MsgBox "Must select a Chapter from the list!"
    Exit Sub
Else
    x = listseleCode
    mprojcodeID = seleproj
    y = writeProjCodeNW(mprojcodeID, x) '<<<<<<<<<<<<<<<<<<<<<<<<<<<<<<<<<<<<<<<<<<<<<<<<<<<<<<<<<
    frmProjCode.Hide
End If
End Sub


Private Sub CommandButton3_Click()
Unload Me
End Sub

Private Sub seleproj_Change()
Me.Repaint
Dim DB As Database
Dim rstProjCodeItem  As Recordset
Dim strProjCodeItem As String
Dim rn As Integer

DBEngine.SystemDB = "\\jwja-svr-10\jdb\JW0610.mdw"
Set DB = OpenDatabase("\\jwja-svr-10\jdb\DB_CODE\2018-Code-01.mdb")
'=============================================================================================================
' Show all laws
'=============================================================================================================
strProjCodeItem_1 = "SELECT rellaw.relLawId, Val([chapterno]) AS vCahpterNo, rellaw.lawno, rellaw.projcodeid " _
& "FROM rellaw " _
& "WHERE (((rellaw.projcodeid) =" & seleproj & ")) " _
& "ORDER BY Val([chapterno]), rellaw.lawno;"

'=============================================================================================================
'=============================================================================================================
' Show Chapters
'=============================================================================================================
strProjCodeItem = "SELECT rellaw.chapterid, Val([chapterno]) AS vCahpterNo, DLookUp('chaptername','chapter','chapterid=' & [chapterid]) AS chaptername, " _
& "rellaw.projcodeid " _
& "FROM rellaw " _
& "GROUP BY rellaw.chapterid, Val([chapterno]), DLookUp('chaptername','chapter','chapterid=' & [chapterid]), rellaw.projcodeid " _
& "HAVING (((rellaw.projcodeid) = " & seleproj & ")) " _
& "ORDER BY Val([chapterno]);"

'=============================================================================================================
'=============================================================================================================


Me.listseleCode.Clear
Set rstProjCodeItem = DB.OpenRecordset(strProjCodeItem)
Debug.Print rn
Do Until rstProjCodeItem.EOF = True
    listseleCode.AddItem rstProjCodeItem!chapterid
    listseleCode.List(listseleCode.ListCount - 1, 1) = rstProjCodeItem!vCahpterNo
    listseleCode.List(listseleCode.ListCount - 1, 2) = rstProjCodeItem!chaptername
    rstProjCodeItem.MoveNext
Loop

End Sub

'==========================================================================================================
' 9/21/18
'==========================================================================================================
Public Sub UserForm_Initialize()
'Dim WS As Workspace
Dim DB As Database
Dim RstProjCode, rstSeleProj As Recordset
Dim strProjCode, strSeleProj As String

' Define the workgroup information file (system database) you will use.
'DBEngine.SystemDB = "C:\Documents and Settings\Jinwoo\Application Data\Microsoft\Access\System6.mdw"
'DBEngine.SystemDB = "C:\Documents and Settings\jwjang\Application Data\Microsoft\Access\system.mdw"
DBEngine.SystemDB = "\\jwja-svr-10\jdb\JW0610.mdw"
' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")

'**********************************************************************************************************
'**********************************************************************************************************
'**********************************************************************************************************
'**********************************************************************************************************

Set DB = OpenDatabase("\\jwja-svr-10\jdb\DB_CODE\2018-Code-01.mdb")
'Set DB = OpenDatabase("H:\db\db_misc\JSPEC04_01.mdb")
'Set DB = OpenDatabase("X:\db_misc\02_Jspec_B_001.mdb")
'Set DB = OpenDatabase("h:\db\db_misc\JSPEC0310.mdb")

'**********************************************************************************************************
'**********************************************************************************************************
'**********************************************************************************************************
' 18/11/11
'Set Rs = DB.OpenRecordset("project")

strSeleProj = "SELECT projcode.projcodeid, projcode.projcodename, projcode.proj_no, Project.PROJ_NAME " _
& "FROM projcode INNER JOIN Project ON projcode.proj_no = Project.PROJ_NO " _
& "ORDER BY projcode.proj_no DESC;"

Set rstSeleProj = DB.OpenRecordset(strSeleProj)

Do Until rstSeleProj.EOF = True

    seleproj.AddItem rstSeleProj!projcodeid
    If IsNull(rstSeleProj!projcodename) = True Then
    seleproj.List(seleproj.ListCount - 1, 1) = ""
    Else
    seleproj.List(seleproj.ListCount - 1, 1) = rstSeleProj!projcodename
    End If
    seleproj.List(seleproj.ListCount - 1, 2) = rstSeleProj!PROJ_NO
    seleproj.List(seleproj.ListCount - 1, 3) = rstSeleProj!PROJ_NAME
    rstSeleProj.MoveNext
Loop
rstSeleProj.Close
Set rstSeleProj = Nothing
DB.Close
Set DB = Nothing

' OPTIONAL: If you set the WS object, use the following to clean up
'WS.Close
'Set WS = Nothing

MsgBox "LOADED!"
End Sub

Attribute VB_Name = "frmSched_CSI"
Attribute VB_Base = "0{457C7058-E07D-4AE4-BEAA-AA9043AF8615}{130AFE5E-35CF-45BB-90B2-D55F24F51904}"
Attribute VB_GlobalNameSpace = False
Attribute VB_Creatable = False
Attribute VB_PredeclaredId = True
Attribute VB_Exposed = False
Attribute VB_TemplateDerived = False
Attribute VB_Customizable = False






Public Sub UserForm_Initialize()
Dim WS As Workspace
Dim DB As Database
Dim rstProj As Recordset
Dim strProj As String

' Define the workgroup information file (system database) you will use.
'DBEngine.SystemDB = "C:\Documents and Settings\Jinwoo\Application Data\Microsoft\Access\System6.mdw"
'DBEngine.SystemDB = "C:\Documents and Settings\jinwoo\Application Data\Microsoft\Access\secured.mdw"
'DBEngine.SystemDB = "C:\Documents and Settings\jwjang\Application Data\Microsoft\Access\system.mdw"
'DBEngine.SystemDB = "X:\JW0610.mdw"
DBEngine.SystemDB = "\\jwja-svr-10\jdb\JW0610.mdw"

' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")
'
'Set DB = OpenDatabase("h:\db\db_07\JPM02_01.mdb")
'Set DB = OpenDatabase("h:\db\db_07\H_H_JPM02_01.mdb")
Set DB = OpenDatabase("\\jwja-svr-10\jdb\DATAS\DT11_JPM_01.mdb")

'Set Rs = DB.OpenRecordset("project")
'SELECT Project.PROJ_NO, Project.PROJ_NAME, Project.STATUS, Project.INPUT
'FROM Project
'WHERE (((Project.Status) = "act"))
'ORDER BY Project.INPUT DESC;

strProj = "SELECT Project.PROJ_NO, Project.PROJ_NAME, Project.STATUS, Project.INPUT " _
& "FROM project " _
& "where (((Project.Status) = 'act'))" _
& "ORDER BY Project.INPUT DESC;"
Set rstProj = DB.OpenRecordset(strProj)
rstProj.MoveLast
rstProj.MoveFirst
Debug.Print rstProj.RecordCount
Do Until rstProj.EOF = True
    seleproj.AddItem rstProj!PROJ_NO
    seleproj.List(seleproj.ListCount - 1, 1) = rstProj!PROJ_NAME
    rstProj.MoveNext
Loop
rstProj.Close
Set rstProj = Nothing
DB.Close
Set DB = Nothing

' OPTIONAL: If you set the WS object, use the following to clean up
'WS.Close
'Set WS = Nothing

MsgBox "Projects Loaded!"

End Sub
Private Sub CheckBox1_Click()

End Sub

Private Sub CommandButton1_Click()
Unload frmSched_CSI
'frmSched_CSI.HIDE

End Sub
Private Sub listSubmission_Click()
'FillSubmission
Dim DB As Database
Dim RstDwg As Recordset
Dim strDwg As String

ListBox4.Clear 'dwgitems

'========================================================================================
' Retired Qry 9/21/18
'========================================================================================
strDwg_old = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, DWGmain.[NO], DWGmain.proj_no, TRADE.TRADENAME " _
& "FROM TRADE INNER JOIN (DWGmain LEFT JOIN DWGGROUP ON DWGmain.DWGGROUP = DWGGROUP.GROUPNO) ON TRADE.TRADEKEY = DWGmain.TRADE " _
& "WHERE (((DWGmain.PROJ_NO) ='" & seleproj & "')) " _
& "ORDER BY TRADE.TRADENO, DWGmain.TRADE, DWGmain.DWGGROUP, Trim([trade] & [dwggroup] & ' ' & [dwgno]);"

'========================================================================================
' New Qry 9/21/18
'========================================================================================
strDwg = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, " _
& "DWGmain.[NO], DWGmain.proj_no, TRADE.TRADENAME, SUBMISSION.SUBID " _
& "FROM (TRADE INNER JOIN (DWGmain LEFT JOIN DWGGROUP ON DWGmain.DWGGROUP = DWGGROUP.GROUPNO) " _
& "ON TRADE.TRADEKEY = DWGmain.TRADE) INNER JOIN (SUBMISSION INNER JOIN SubItem ON SUBMISSION.SUBID = SubItem.subid) ON DWGmain.ID = SubItem.subdwg " _
& "WHERE (((SUBMISSION.SUBID) = " & listSubmission & ")) " _
& "ORDER BY TRADE.TRADENO, DWGmain.TRADE, DWGmain.DWGGROUP, Trim([trade] & [dwggroup] & ' ' & [dwgno]);"

strDwg_test = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, " _
& "DWGmain.[NO], DWGmain.proj_no, TRADE.TRADENAME "

Set DB = OpenDatabase("\\jwja-svr-10\jdb\db_misc\X-dwg.mdb")

Set RstDwg = DB.OpenRecordset(strDwg)

Do Until RstDwg.EOF = True
    ListBox4.AddItem RstDwg!DWGNUMBER
    If IsNull(RstDwg!DWGNAME) = False Then
    ListBox4.List(ListBox4.ListCount - 1, 1) = RstDwg!DWGNAME
    End If
    RstDwg.MoveNext
Loop
RstDwg.Close
Set RstDwg = Nothing


DB.Close
Set DB = Nothing

End Sub

Private Sub seleproj_Change()
'===================================================================================
' DWG
'===================================================================================

Dim DB As Database
Dim RstDwg As Recordset
Dim strDwg As String
'DBEngine.SystemDB = "C:\Documents and Settings\Jinwoo\Application Data\Microsoft\Access\secured.mdw"

Set DB = OpenDatabase("\\jwja-svr-10\jdb\db_misc\X-dwg.mdb")
'------------------------------------------------------------------------

listSubmission.Clear
strSub = "SELECT SUBMISSION.SUBID, SUBMISSION.SUBDATE, SUBMISSION.SUBNO, SUBMISSION.SUBNAME, SUBMISSION.PROJ_NO " _
& "FROM SUBMISSION " _
& "WHERE (((SUBMISSION.PROJ_NO)='" & seleproj & "'))"
Set RstSub = DB.OpenRecordset(strSub)
Do Until RstSub.EOF = True
    listSubmission.AddItem RstSub!SUBID
    If IsNull(RstSub!subname) = False Then
    'RstSub.AddItem RstSub!subid
    listSubmission.List(listSubmission.ListCount - 1, 1) = RstSub!subname
    End If
    RstSub.MoveNext
Loop
RstSub.Close
Set RstSub = Nothing
'------------------------------------------------------------------------
ListBox1.Clear 'dwgitems

'========================================================================================
' Retired Qry 9/21/18
'========================================================================================
strDwg = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, DWGmain.[NO], DWGmain.proj_no, TRADE.TRADENAME " _
& "FROM TRADE INNER JOIN (DWGmain LEFT JOIN DWGGROUP ON DWGmain.DWGGROUP = DWGGROUP.GROUPNO) ON TRADE.TRADEKEY = DWGmain.TRADE " _
& "WHERE (((DWGmain.PROJ_NO) ='" & seleproj & "')) " _
& "ORDER BY TRADE.TRADENO, DWGmain.TRADE, DWGmain.DWGGROUP, Trim([trade] & [dwggroup] & ' ' & [dwgno]);"

'========================================================================================
' New Qry 9/21/18
'========================================================================================
strDwg_New = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, " _
& "DWGmain.[NO], DWGmain.proj_no, TRADE.TRADENAME, SUBMISSION.SUBID " _
& "FROM (TRADE INNER JOIN (DWGmain LEFT JOIN DWGGROUP ON DWGmain.DWGGROUP = DWGGROUP.GROUPNO) " _
& "ON TRADE.TRADEKEY = DWGmain.TRADE) INNER JOIN (SUBMISSION INNER JOIN SubItem ON SUBMISSION.SUBID = SubItem.subid) ON DWGmain.ID = SubItem.subdwg " _
& "WHERE (((SUBMISSION.SUBID) = '" & listSubmission & "')) " _
& "ORDER BY TRADE.TRADENO, DWGmain.TRADE, DWGmain.DWGGROUP, Trim([trade] & [dwggroup] & ' ' & [dwgno]);"



Set RstDwg = DB.OpenRecordset(strDwg)

Do Until RstDwg.EOF = True
    ListBox1.AddItem RstDwg!DWGNUMBER
    If IsNull(RstDwg!DWGNAME) = False Then
    ListBox1.List(ListBox1.ListCount - 1, 1) = RstDwg!DWGNAME
    End If
    RstDwg.MoveNext
Loop
RstDwg.Close
Set RstDwg = Nothing


DB.Close
Set DB = Nothing
'===================================================================================
' FIXTURE_NEW WITH [PROFIXLIST]
'===================================================================================
Set DB = OpenDatabase("\\jwja-svr-10\jdb\db_FIX\X-FIXTURE_17_01.mdb")
ListBox5.Clear
strProFixList = "SELECT PROFIXLIST.PROJ_NO, PROFIXLIST.PROFIXLISTID, PROFIXLIST.PROFIXLISTNAME, PROFIXLIST.PROFIXLISTDATE " _
& "FROM PROFIXLIST " _
& "WHERE (((PROFIXLIST.PROJ_NO)='" & seleproj & "')) " _
& "ORDER BY PROFIXLISTID;"
Set RstProFixList = DB.OpenRecordset(strProFixList)

Do Until RstProFixList.EOF = True
    If IsNull(RstProFixList!PROFIXLISTID) = False Then

    ListBox5.AddItem RstProFixList!PROFIXLISTID
    ListBox5.List(ListBox5.ListCount - 1, 1) = RstProFixList!PROFIXLISTNAME
    End If
    RstProFixList.MoveNext
Loop
RstProFixList.Close
Set RstProFixList = Nothing
DB.Close
Set DB = Nothing
'---------------------------------------------
' 11/3/18
'---------------------------------------------


'===================================================================================
' FIXTURE_OLD
'===================================================================================
'Set DB = OpenDatabase("\\jwja-svr-10\jdb\db_FIX\X-FIXTURE_17_01.mdb")

'ListBox2.Clear
'strFXType = "SELECT FIXITEM.FXTYPE " _
'& "FROM FIXITEM INNER JOIN PROFIX ON FIXITEM.FXID = PROFIX.FXID " _
'& "GROUP BY PROFIX.PROJ_NO, FIXITEM.FXTYPE " _
'& "HAVING (((PROFIX.PROJ_NO) = '" & seleproj & "')) " _
'& "ORDER BY FIXITEM.FXTYPE;"

'Set RstFXType = DB.OpenRecordset(strFXType)

'Do Until RstFXType.EOF = True
'    If IsNull(RstFXType!FXTYPE) = False Then

'    ListBox2.AddItem RstFXType!FXTYPE
'    'ListBox1.List(ListBox1.ListCount - 1, 1) = RstFXType!DWGNAME
'    End If
'    RstFXType.MoveNext
'Loop
'RstFXType.Close
'Set RstFXType = Nothing
'DB.Close
'Set DB = Nothing
'===================================================================================
' LIGHT
'===================================================================================

Set DB = OpenDatabase("\\jwja-svr-10\jdb\db_misc\X-light.mdb")

ListBox3.Clear
strLight = "SELECT PROFIX.PROJ_NO, PROFIX.PFXNO, FIXITEM.FXTYPE, FIXITEM.FXMODEL " _
& "FROM FIXITEM INNER JOIN PROFIX ON FIXITEM.FXID = PROFIX.FXID " _
& "WHERE (((PROFIX.PROJ_NO)='" & seleproj & "'))" _
& "ORDER BY PROFIX.PFXNO;"

'& "HAVING (((PROFIX.PROJ_NO) = '" & seleproj & "')) " _
'& "ORDER BY PROFIX.PFXNO;"

Set RstLight = DB.OpenRecordset(strLight)
Debug.Print RstLight.RecordCount
If RstLight.RecordCount = 0 Then
    Exit Sub
Else
x = RstLight.RecordCount
Do Until RstLight.EOF = True
    If IsNull(RstLight!FXtype) = False Then
    x = RstLight.RecordCount
        If RstLight!PFXNO = "" Then
            GoTo SKIPFORNEXTLIGHT
        Else
            ListBox3.AddItem RstLight!PFXNO
            ListBox3.List(ListBox3.ListCount - 1, 1) = RstLight!FXMODEL
            'ListBox3.List(ListBox3.ListCount - 1, 2) = RstLight!fx
        End If
    End If
SKIPFORNEXTLIGHT:
    RstLight.MoveNext
Loop
RstLight.Close
Set RstLight = Nothing
DB.Close
Set DB = Nothing
End If
End Sub
Private Sub ListBox5_Click()
'=====================================
' 11/3/18
'=====================================
ListBox2.Clear 'FXTYPE
Dim DB As Database
Dim RSTPROFIX As Recordset
'strFXType = "SELECT FIXITEM.FXTYPE " _
& "FROM FIXITEM INNER JOIN PROFIX ON FIXITEM.FXID = PROFIX.FXID " _
& "GROUP BY PROFIX.PROJ_NO, FIXITEM.FXTYPE " _
& "HAVING (((PROFIX.PROJ_NO) = '" & seleproj & "')) " _
& "ORDER BY FIXITEM.FXTYPE;"



strProFix = "SELECT PROFIX.PROFIXLISTID, FIXITEM.FXTYPE " _
& "FROM FIXITEM INNER JOIN PROFIX ON FIXITEM.FXID = PROFIX.FXID " _
& "GROUP BY PROFIX.PROFIXLISTID, FIXITEM.FXTYPE " _
& "HAVING (PROFIX.PROFIXLISTID) = " & ListBox5 _
& " ORDER BY FIXITEM.FXTYPE;"

Set DB = OpenDatabase("\\jwja-svr-10\jdb\db_FIX\X-FIXTURE_17_01.mdb")

Set RSTPROFIX = DB.OpenRecordset(strProFix)

Do Until RSTPROFIX.EOF = True
    If IsNull(RSTPROFIX!FXtype) = False Then

    ListBox2.AddItem RSTPROFIX!FXtype
    'ListBox2.List(ListBox2.ListCount - 1, 1) = RSTPROFIX!PFXNO
    End If
    RSTPROFIX.MoveNext
Loop
RSTPROFIX.Close
Set RSTPROFIX = Nothing
DB.Close
Set DB = Nothing

End Sub


Private Sub CommandButton2_Click() 'Old DWG List Button
Dim DB As Database
Dim RstDwg, RstTrade As Recordset
Dim strDwg, strTrade As String
Dim rcTrade, rcDwg As Integer
Dim TblPT(0 To 2) As Double
Dim tblPT2(0 To 2) As Double
Dim tblWidth As Double
Dim txtHt As Double
Dim textObj As AcadText
Dim attributeObj As AcadAttribute
Dim height As Double
Dim mode As Long
Dim prompt As String
'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

Set DB = OpenDatabase("\\jwja-svr-10\jdb\db_misc\X-dwg.mdb")

strTrade = "SELECT TRADE.TRADENAME, TRADE.TRADENO, DWGmain.proj_no " _
& "FROM TRADE LEFT JOIN DWGmain ON TRADE.TRADEKEY = DWGmain.TRADE " _
& "GROUP BY TRADE.TRADENAME, TRADE.TRADENO, DWGmain.proj_no " _
& "HAVING (((DWGmain.proj_no)='" & seleproj & "'));"

Set RstTrade = DB.OpenRecordset(strTrade)

TblPT(0) = 0: TblPT(1) = 0: TblPT(2) = 0
tblPT2(0) = -300: tblPT2(1) = 0: tblPT2(2) = 0
txtHt = 4
txtRow = ""
mode = acAttributeModeVerify

ThisDrawing.ModelSpace.InsertBlock TblPT, "\\jwja-svr-10\drawfile\jvba\XDWGHEAD01.dwg", 1, 1, 1, 0
InsertJBlock "\\jwja-svr-10\drawfile\jvba\XDWGTRADE01.dwg", tblPT2, "Model"
InsertJBlock "\\jwja-svr-10\drawfile\jvba\XDWGROW01.dwg", tblPT2, "Model"
'InsertJBlock "e:\drawfile\jvba\XHDWRFOOT02.dwg", tblPT2, "Model"
TblPT(1) = TblPT(1) - 36 'HEAD
Set RstTrade = DB.OpenRecordset(strTrade)
RstTrade.MoveLast
RstTrade.MoveFirst
rcTrade = RstTrade.RecordCount
Debug.Print rcTrade
With RstTrade
    For i = 1 To rcTrade
        ' xHDWRSETID = !HDWRSETID
         Set blockRefObj = ThisDrawing.ModelSpace.InsertBlock _
                     (TblPT, "XDWGTRADE01", 1, 1, 1, 0)
            Dim varAttributes As Variant
            varAttributes = blockRefObj.GetAttributes
            For iatTrade = LBound(varAttributes) To UBound(varAttributes)
            
            Debug.Print varAttributes(iatTrade).TagString
                If varAttributes(iatTrade).TagString = "XTRADENAME" Then
                    If IsNull(!TRADENAME) = True Then
                        varAttributes(iatTrade).textString = ""
                    Else
                        varAttributes(iatTrade).textString = !TRADENAME
                        Debug.Print varAttributes(iatTrade).textString
                    End If

                End If
                If varAttributes(iatTrade).TagString = "XTRADENO" Then
                    If IsNull(!TRADENO) = True Then
                        varAttributes(iatTrade).textString = ""
                    Else
                        varAttributes(iatTrade).textString = !TRADENO
                    End If

                End If
            Next iatTrade
            
                TblPT(1) = TblPT(1) - 18 'TRADE
                xTRADENO = !TRADENO
                Debug.Print xTRADENO
'_____________________________________________________________________________________
                strDwg = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, DWGmain.NO, DWGmain.proj_no, TRADE.TRADENAME " _
& "FROM TRADE INNER JOIN (DWGmain LEFT JOIN DWGGROUP ON DWGmain.DWGGROUP = DWGGROUP.GROUPNO) ON TRADE.TRADEKEY = DWGmain.TRADE " _
& "WHERE (((DWGmain.PROJ_NO) ='" & seleproj & "')) and trade.tradeno =" & xTRADENO _
& " ORDER BY TRADE.TRADENO, DWGmain.TRADE, DWGmain.DWGGROUP, Trim([trade] & [dwggroup] & ' ' & [dwgno]);"

                Set RstDwg = DB.OpenRecordset(strDwg)
                Debug.Print RstDwg.RecordCount
                'Debug.Print strHDSet

                
                If RstDwg.RecordCount = 0 Then
                    GoTo EXITDWG
                End If
                RstDwg.MoveLast
                RstDwg.MoveFirst
                Debug.Print RstDwg.RecordCount
                Debug.Print rcDwg
                rcDwg = RstDwg.RecordCount
                With RstDwg
                Debug.Print xTRADENO
                    For k = 1 To rcDwg
                         Set blockRefObj = ThisDrawing.ModelSpace.InsertBlock _
                                     (TblPT, "XDWGROW01", 1, 1, 1, 0)
                        Dim varAttributes2 As Variant
                        varAttributes2 = blockRefObj.GetAttributes
                        For iatDWG = LBound(varAttributes2) To UBound(varAttributes2)
                        Debug.Print varAttributes2(iatDWG).TagString
                            If varAttributes2(iatDWG).TagString = "XDWGNO" Then
                                If IsNull(!no) = True Then
                                    varAttributes2(iatDWG).textString = ""
                                Else
                                    varAttributes2(iatDWG).textString = !no
                                End If
                            End If
                            If varAttributes2(iatDWG).TagString = "XDWGNAME" Then
                                If IsNull(!DWGNAME) = True Then
                                    varAttributes2(iatDWG).textString = ""
                                Else
                                    varAttributes2(iatDWG).textString = !DWGNAME
                                End If
                            End If
                            If varAttributes2(iatDWG).TagString = "XDATE" Then
                                If IsNull(!Date) = True Then
                                    varAttributes2(iatDWG).textString = ""
                                Else
                                    varAttributes2(iatDWG).textString = !Date
                                End If
                            End If
                            If varAttributes2(iatDWG).TagString = "XREV" Then
                                If IsNull(!REV) = True Then
                                    varAttributes2(iatDWG).textString = ""
                                Else
                                    varAttributes2(iatDWG).textString = !REV
                                End If
                            End If
                            If varAttributes2(iatDWG).TagString = "XNOTE1" Then
                                If IsNull(!GENnote) = True Then
                                    varAttributes2(iatDWG).textString = ""
                                Else
                                    varAttributes2(iatDWG).textString = !GENnote
                                End If
                            End If
                        Next iatDWG
                        TblPT(1) = TblPT(1) - 12 'ROW
                        .MoveNext
                    Next k
                    End With
                'tblPT(1) = tblPT(1) - 12
                .MoveNext
                Next i
                End With

EXITDWG:


RstTrade.Close

RstDwg.Close
Set rsttrad = Nothing
Set RstDwg = Nothing
DB.Close
Set DB = Nothing
frmSched_CSI.Hide
End Sub
Private Sub CommandButton5_Click() 'New DWG List Button
Dim DB As Database
Dim RstDwg, RstTrade As Recordset
Dim strDwg, strTrade As String
Dim rcTrade, rcDwg As Integer
Dim TblPT(0 To 2) As Double
Dim tblPT2(0 To 2) As Double
Dim tblWidth As Double
Dim txtHt As Double
Dim textObj As AcadText
Dim attributeObj As AcadAttribute
Dim height As Double
Dim mode As Long
Dim prompt As String
'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

Set DB = OpenDatabase("\\jwja-svr-10\jdb\db_misc\X-dwg.mdb")

strTrade = "SELECT TRADE.TRADENAME, TRADE.TRADENO, DWGmain.proj_no " _
& "FROM TRADE LEFT JOIN DWGmain ON TRADE.TRADEKEY = DWGmain.TRADE " _
& "GROUP BY TRADE.TRADENAME, TRADE.TRADENO, DWGmain.proj_no " _
& "HAVING (((DWGmain.proj_no)='" & seleproj & "'));"

Set RstTrade = DB.OpenRecordset(strTrade)

TblPT(0) = 0: TblPT(1) = 0: TblPT(2) = 0
tblPT2(0) = -300: tblPT2(1) = 0: tblPT2(2) = 0
txtHt = 4
txtRow = ""
mode = acAttributeModeVerify

ThisDrawing.ModelSpace.InsertBlock TblPT, "\\jwja-svr-10\drawfile\jvba\XDWGHEAD01.dwg", 1, 1, 1, 0
InsertJBlock "\\jwja-svr-10\drawfile\jvba\XDWGTRADE01.dwg", tblPT2, "Model"
InsertJBlock "\\jwja-svr-10\drawfile\jvba\XDWGROW01.dwg", tblPT2, "Model"
'InsertJBlock "e:\drawfile\jvba\XHDWRFOOT02.dwg", tblPT2, "Model"
TblPT(1) = TblPT(1) - 36 'HEAD
Set RstTrade = DB.OpenRecordset(strTrade)
RstTrade.MoveLast
RstTrade.MoveFirst
rcTrade = RstTrade.RecordCount
Debug.Print rcTrade
With RstTrade
    For i = 1 To rcTrade
        ' xHDWRSETID = !HDWRSETID
         Set blockRefObj = ThisDrawing.ModelSpace.InsertBlock _
                     (TblPT, "XDWGTRADE01", 1, 1, 1, 0)
            Dim varAttributes As Variant
            varAttributes = blockRefObj.GetAttributes
            For iatTrade = LBound(varAttributes) To UBound(varAttributes)
            
            Debug.Print varAttributes(iatTrade).TagString
                If varAttributes(iatTrade).TagString = "XTRADENAME" Then
                    If IsNull(!TRADENAME) = True Then
                        varAttributes(iatTrade).textString = ""
                    Else
                        varAttributes(iatTrade).textString = !TRADENAME
                        Debug.Print varAttributes(iatTrade).textString
                    End If

                End If
                If varAttributes(iatTrade).TagString = "XTRADENO" Then
                    If IsNull(!TRADENO) = True Then
                        varAttributes(iatTrade).textString = ""
                    Else
                        varAttributes(iatTrade).textString = !TRADENO
                    End If

                End If
            Next iatTrade
            
                TblPT(1) = TblPT(1) - 18 'TRADE
                xTRADENO = !TRADENO
                Debug.Print xTRADENO
'_____________________________________________________________________________________
'==========================================================================================================================
' 9/21/18
'==========================================================================================================================

                strDwg_old = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, DWGmain.NO, DWGmain.proj_no, TRADE.TRADENAME " _
& "FROM TRADE INNER JOIN (DWGmain LEFT JOIN DWGGROUP ON DWGmain.DWGGROUP = DWGGROUP.GROUPNO) ON TRADE.TRADEKEY = DWGmain.TRADE " _
& "WHERE (((DWGmain.PROJ_NO) ='" & seleproj & "')) and trade.tradeno =" & xTRADENO _
& " ORDER BY TRADE.TRADENO, DWGmain.TRADE, DWGmain.DWGGROUP, Trim([trade] & [dwggroup] & ' ' & [dwgno]);"
'==========================================================================================================================
'strDwg = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, " _
& "DWGmain.[NO], DWGmain.proj_no, TRADE.TRADENAME, SUBMISSION.SUBID " _
& "FROM TRADE INNER JOIN (DWGmain LEFT JOIN DWGGROUP ON DWGmain.DWGGROUP = DWGGROUP.GROUPNO) " _
& "ON TRADE.TRADEKEY = DWGmain.TRADE) INNER JOIN (SUBMISSION INNER JOIN SubItem ON SUBMISSION.SUBID = SubItem.subid) ON DWGmain.ID = SubItem.subdwg " _
& "WHERE (((SUBMISSION.SUBID) = " & listSubmission & ")) And trade.tradeno =" & xTRADENO _
& "ORDER BY TRADE.TRADENO, DWGmain.TRADE, DWGmain.DWGGROUP, Trim([trade] & [dwggroup] & ' ' & [dwgno]);"
'==========================================================================================================================
strDwg_notworking = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, DWGmain.NO, DWGmain.proj_no, TRADE.TRADENAME " _
& "FROM TRADE INNER JOIN (DWGmain LEFT JOIN DWGGROUP ON DWGmain.DWGGROUP = DWGGROUP.GROUPNO) ON TRADE.TRADEKEY = DWGmain.TRADE " _
& "INNER JOIN (SUBMISSION INNER JOIN SubItem ON SUBMISSION.SUBID = SubItem.subid) ON DWGmain.ID = SubItem.subdwg " _
& "WHERE trade.tradeno =" & xTRADENO & " and (SUBMISSION.SUBID) = " & listSubmission & "))" _
& "ORDER BY TRADE.TRADENO, DWGmain.TRADE, DWGmain.DWGGROUP, Trim([trade] & [dwggroup] & ' ' & [dwgno]);"

strDwg = "SELECT TRADE.TRADENO, DWGmain.ID, DWGmain.TRADE, DWGmain.DWGGROUP, " _
& "Trim([trade] & [dwggroup] & ' ' & [dwgno]) AS dwgnumber, DWGmain.SECTOR, " _
& "DWGmain.DWGNO, DWGmain.DWGNAME, DWGmain.DATE, DWGmain.REV, DWGmain.COMPLETE, " _
& "DWGmain.CREATEDBY, DWGmain.GENnote, DWGmain.taskid, DWGmain.NOTEID, DWGGROUP.GROUPNAME, DWGmain.[NO], DWGmain.proj_no, TRADE.TRADENAME, SUBMISSION.SUBID " _
& "FROM (TRADE INNER JOIN (DWGmain LEFT JOIN DWGGROUP ON DWGmain.DWGGROUP = DWGGROUP.GROUPNO) ON TRADE.TRADEKEY = DWGmain.TRADE) " _
& "INNER JOIN (SUBMISSION INNER JOIN SubItem ON SUBMISSION.SUBID = SubItem.subid) ON DWGmain.ID = SubItem.subdwg " _
& "WHERE (((TRADE.TRADENO) =" & xTRADENO & ") And ((SUBMISSION.SUBID) =" & listSubmission & ")) " _
& "ORDER BY TRADE.TRADENO, DWGmain.TRADE, DWGmain.DWGGROUP, Trim([trade] & [dwggroup] & ' ' & [dwgno]);"

'==========================================================================================================================
' 9/21/18
'==========================================================================================================================
                Set RstDwg = DB.OpenRecordset(strDwg)
                Debug.Print RstDwg.RecordCount
                'Debug.Print strHDSet

                
                If RstDwg.RecordCount = 0 Then
                    GoTo EXITDWG
                End If
                RstDwg.MoveLast
                RstDwg.MoveFirst
                Debug.Print RstDwg.RecordCount
                Debug.Print rcDwg
                rcDwg = RstDwg.RecordCount
                With RstDwg
                Debug.Print xTRADENO
                    For k = 1 To rcDwg
                         Set blockRefObj = ThisDrawing.ModelSpace.InsertBlock _
                                     (TblPT, "XDWGROW01", 1, 1, 1, 0)
                        Dim varAttributes2 As Variant
                        varAttributes2 = blockRefObj.GetAttributes
                        For iatDWG = LBound(varAttributes2) To UBound(varAttributes2)
                        Debug.Print varAttributes2(iatDWG).TagString
                            If varAttributes2(iatDWG).TagString = "XDWGNO" Then
                                If IsNull(!no) = True Then
                                    varAttributes2(iatDWG).textString = ""
                                Else
                                    varAttributes2(iatDWG).textString = !no
                                End If
                            End If
                            If varAttributes2(iatDWG).TagString = "XDWGNAME" Then
                                If IsNull(!DWGNAME) = True Then
                                    varAttributes2(iatDWG).textString = ""
                                Else
                                    varAttributes2(iatDWG).textString = !DWGNAME
                                End If
                            End If
                            If varAttributes2(iatDWG).TagString = "XDATE" Then
                                If IsNull(!Date) = True Then
                                    varAttributes2(iatDWG).textString = ""
                                Else
                                    varAttributes2(iatDWG).textString = !Date
                                End If
                            End If
                            If varAttributes2(iatDWG).TagString = "XREV" Then
                                If IsNull(!REV) = True Then
                                    varAttributes2(iatDWG).textString = ""
                                Else
                                    varAttributes2(iatDWG).textString = !REV
                                End If
                            End If
                            If varAttributes2(iatDWG).TagString = "XNOTE1" Then
                                If IsNull(!GENnote) = True Then
                                    varAttributes2(iatDWG).textString = ""
                                Else
                                    varAttributes2(iatDWG).textString = !GENnote
                                End If
                            End If
                        Next iatDWG
                        TblPT(1) = TblPT(1) - 12 'ROW
                        .MoveNext
                    Next k
                    End With
                'tblPT(1) = tblPT(1) - 12
                .MoveNext
                Next i
                End With

EXITDWG:


RstTrade.Close

RstDwg.Close
Set rsttrad = Nothing
Set RstDwg = Nothing
DB.Close
Set DB = Nothing
frmSched_CSI.Hide
End Sub


Sub LIGHT()
Dim DB As Database
Dim RstFix As Recordset
Dim strLight As String
Dim rcFix, iatFix, iatType As Integer
Dim TblPT(0 To 2) As Double
Dim tblPT2(0 To 2) As Double
Dim tblWidth As Double
Dim txtHt As Double
Dim textObj As AcadText
Dim attributeObj As AcadAttribute
Dim height As Double
Dim mode As Long
Dim nHeadDwg, nRowDwg As Variant
Dim nJumpHead, nJumpRow As Integer
'Dim tag As String
'Dim value As String
Dim blockRefObj As AcadBlockReference
'Dim attData() As AcadObject

'Dim FilterGp(0) As Integer
'Dim FilterDt(0) As Variant
Dim BlkObj As Object
'Dim Pt1(0) As Double
'Dim Pt2(0) As Double

'Dim oSset As AcadSelectionSet



Set DB = OpenDatabase("\\jwja-svr-10\jdb\db_misc\X-light.mdb")

strLight = "SELECT FIXITEM.FXTYPE, PROFIX.PFXID, FIXITEM.FXID, PROFIX.PFXNO, PROFIX.PROJ_NO, PROFIX.PFXRM, PROFIX.Pfxnote, " _
& "FIXITEM.FXMFGR, FIXITEM.FXMODEL, FIXITEM.FXCAT, FIXITEM.FXCOLOR, FIXITEM.FXIMGNAME, FIXITEM.FXLISTPRICE, PROFIX.FXDISCOUNT, " _
& "PROFIX.FXPRICE, PROFIX.FXTAX, FIXITEM.FXLEAD, FIXITEM.fxnote, Project.PROJ_NAME, Project.PROJ_ADDR, Project.PROJ_CITY, " _
& "Project.PROJ_STATE, Project.PROJ_ZIP, PROFIX.FXQTY, PROFIX.FXPRNOTE, Contact.COMPANY, LTSUP.LTBULB, LTSUP.LTBULBQTY, " _
& "LTSUP.LTVOLT, BULB.BUBTYPE, BULB.BUBMODEL, BULB.BUBCAT, BULB.BUBTEMP, BULB.BUBMFGR, BULB.BUBWATT, FIXITEM.FXMFGR, " _
& "Contact.COMPANY, Contact.STREET, Contact.CITY, Contact.STATE, Contact.ZIP, Contact.TEL_BUS, Trim([CONTACT].[CITY] & ', ' & [CONTACT].[STATE] & ' ' & [CONTACT].[ZIP]) AS SCSZ, " _
& "Contact_1.COMPANY, Contact_1.STREET, Contact_1.CITY, Contact_1.STATE, Contact_1.ZIP, Contact_1.TEL_BUS, Trim([CONTACT_1].[CITY] & ', ' & [CONTACT_1].[STATE] & ' ' & [CONTACT_1].[ZIP]) AS MCSZ " _
& "FROM ((((Contact RIGHT JOIN FIXITEM ON Contact.CID = FIXITEM.FXSUPPLIER) LEFT JOIN LTSUP ON FIXITEM.FXID = LTSUP.FXID) " _
& "LEFT JOIN BULB ON LTSUP.LTBULB = BULB.BUBID) LEFT JOIN Contact AS Contact_1 ON FIXITEM.FXMFGR = Contact_1.CID) " _
& "INNER JOIN (Project RIGHT JOIN PROFIX ON Project.PROJ_NO = PROFIX.PROJ_NO) ON FIXITEM.FXID = PROFIX.FXID " _
& "WHERE (((PROFIX.PROJ_NO) ='" & seleproj & "')) " _
& "ORDER BY FIXITEM.FXTYPE, PROFIX.PFXNO;"

'& "WHERE (((FIXITEM.fxtype) = [FORMS]![FRMFIX]![fxtype]) And ((PROFIX.PROJ_NO) ='" & seleproj & "')) " _





'strFix = "SELECT FIXITEM.FXTYPE, PROFIX.PFXID, FIXITEM.FXID, PROFIX.PFXNO, PROFIX.PROJ_NO, PROFIX.PFXRM, " _
& "PROFIX.Pfxnote, FIXITEM.FXSUPPLIER, FIXITEM.FXMODEL, FIXITEM.FXCAT, FIXITEM.FXCOLOR, FIXITEM.FXLISTPRICE, " _
& "PROFIX.FXDISCOUNT, PROFIX.FXPRICE, PROFIX.FXTAX, FIXITEM.FXLEAD, FIXITEM.fxnote, PROFIX.FXQTY, PROFIX.FXPRNOTE, " _
& "Contact.COMPANY, Contact_1.COMPANY, FIXITEM.FXIMGNAME, Contact.RELATION, Contact.LAST, Contact.FIRST, " _
& "Contact.TEL_BUS, Contact.TEL_FAX, Contact.EMAIL, Contact.STREET, Contact.CITY, Contact.STATE, Contact.ZIP, " _
& "Contact_1.RELATION, Contact_1.LAST, Contact_1.FIRST, Contact_1.TITLE, Contact_1.TEL_BUS, Contact_1.TEL_FAX, " _
& "Contact_1.EMAIL, Contact_1.STREET, Contact_1.CITY, Contact_1.STATE, Contact_1.ZIP, PROFIX.FXEXIST, FIXITEM.FXIMGSIM, " _
& "PROFIX.FXPRNOTE, PROFIX.COMMENT, FIXITEM.FXNAME, Trim([CONTACT].[CITY] & ', ' & [CONTACT].[STATE] & ' ' & [CONTACT].[ZIP]) AS SCSZ, " _
& "Trim([CONTACT_1].[CITY] & ', ' & [CONTACT_1].[STATE] & ' ' & [CONTACT_1].[ZIP]) AS MCSZ FROM ((Contact RIGHT JOIN FIXITEM ON Contact.CID = FIXITEM.FXSUPPLIER) " _
& "LEFT JOIN Contact AS Contact_1 ON FIXITEM.FXMFGR = Contact_1.CID) INNER JOIN PROFIX ON FIXITEM.FXID = PROFIX.FXID " _
& "WHERE (((FIXITEM.FXtype) ='" & ListBox2 & "') And ((PROFIX.PROJ_NO) ='" & seleproj & "')) " _
& "ORDER BY PROFIX.PFXID, FIXITEM.FXID, PROFIX.PFXNO;"

'Trim(CONTACT_1.CITY & ', ' & CONTACT_1.STATE & ' ' & CONTACT_1.ZIP) AS SCSZ
'strFix = "SELECT FIXITEM.FXTYPE, PROFIX.PFXID, FIXITEM.FXID, PROFIX.PFXNO, PROFIX.PROJ_NO, PROFIX.PFXRM, " _
& "PROFIX.Pfxnote, FIXITEM.FXSUPPLIER, FIXITEM.FXMODEL, FIXITEM.FXCAT, FIXITEM.FXCOLOR, FIXITEM.FXLISTPRICE, " _
& "PROFIX.FXDISCOUNT, PROFIX.FXPRICE, PROFIX.FXTAX, FIXITEM.FXLEAD, FIXITEM.fxnote, PROFIX.FXQTY, PROFIX.FXPRNOTE, " _
& "Contact.COMPANY, Contact_1.COMPANY, FIXITEM.FXIMGNAME, Contact.RELATION, Contact.LAST, Contact.FIRST, " _
& "Contact.TEL_BUS, Contact.TEL_FAX, Contact.EMAIL, Contact.STREET, Contact.CITY, Contact.STATE, Contact.ZIP, " _
& "Contact_1.RELATION, Contact_1.LAST, Contact_1.FIRST, Contact_1.TITLE, Contact_1.TEL_BUS, Contact_1.TEL_FAX, " _
& "Contact_1.EMAIL, Contact_1.STREET, Contact_1.CITY, Contact_1.STATE, Contact_1.ZIP, PROFIX.FXEXIST, FIXITEM.FXIMGSIM " _
& "FROM ((Contact RIGHT JOIN FIXITEM ON Contact.CID = FIXITEM.FXSUPPLIER) " _
& "LEFT JOIN Contact AS Contact_1 ON FIXITEM.FXMFGR = Contact_1.CID) INNER JOIN PROFIX ON FIXITEM.FXID = PROFIX.FXID " _
& "WHERE (((FIXITEM.FXtype) ='" & ListBox2 & "') And ((PROFIX.PROJ_NO) ='" & seleproj & "')) " _
& "ORDER BY PROFIX.PFXID, FIXITEM.FXID, PROFIX.PFXNO;"


TblPT(0) = 0: TblPT(1) = 0: TblPT(2) = 0
tblPT2(0) = -500: tblPT2(1) = 0: tblPT2(2) = 0
txtHt = 4
txtRow = ""
mode = acAttributeModeVerify
If ShowImage = True Then
    nHeadDwg = "\\jwja-svr-10\drawfile\jvba\XLIGHTHEAD02.dwg"
    nRowDwg = "\\jwja-svr-10\drawfile\jvba\XLIGHTROW02.dwg"
    nJumpHead = 60
    nJumpRow = 60
    InsertJBlock "\\jwja-svr-10\drawfile\jvba\XLIGHTHEAD02.dwg", tblPT2, "Model"
Else
    nHeadDwg = "\\jwja-svr-10\drawfile\jvba\XLIGHTHEAD01.dwg"
    nRowDwg = "\\jwja-svr-10\drawfile\jvba\XLIGHTROW01.dwg"
    nJumpHead = 48
    nJumpRow = 24
    InsertJBlock "\\jwja-svr-10\drawfile\jvba\XLIGHTHEAD01.dwg", tblPT2, "Model"

End If
'ThisDrawing.ModelSpace.InsertBlock tblPT, "H:\drawfile\jvba\XFIXHEAD01.dwg", 1, 1, 1, 0
'InsertJBlock "H:\drawfile\jvba\XDWGTRADE01.dwg", tblPT2, "Model"
'InsertJBlock nHeadDwg, tblPT2, "Model"
'InsertJBlock "e:\drawfile\jvba\XHDWRFOOT02.dwg", tblPT2, "Model"
'tblPT(1) = tblPT(1) - 48

Set RstFix = DB.OpenRecordset(strLight)
RstFix.MoveLast
RstFix.MoveFirst
rcFix = RstFix.RecordCount
Debug.Print rcFix
With RstFix
Set blockRefObj2 = ThisDrawing.ModelSpace.InsertBlock _
                     (TblPT, nHeadDwg, 1, 1, 1, 0)
Dim varAttributes2 As Variant
varAttributes2 = blockRefObj2.GetAttributes
For iatType = LBound(varAttributes2) To UBound(varAttributes2)

Debug.Print varAttributes2(iatType).TagString
    If varAttributes2(iatType).TagString = "XTYPE" Then
        If IsNull(!FXtype) = True Then
            varAttributes2(iatType).textString = ""
        Else
            varAttributes2(iatType).textString = !FXtype & " FIXTURE SCHEDULE"
            Debug.Print varAttributes2(iatType).textString
        End If
    End If
    If varAttributes2(iatType).TagString = "XPROJ_NO" Then
        If IsNull(!PROJ_NO) = True Then
            varAttributes2(iatType).textString = ""
        Else
            varAttributes2(iatType).textString = !PROJ_NO
            Debug.Print varAttributes2(iatType).textString
        End If
    End If
    If varAttributes2(iatType).TagString = "XDATE" Then
        'If IsNull(!fxtype) = True Then
            'varAttributes2(iatType).TextString = ""
        'Else
            varAttributes2(iatType).textString = Date
            Debug.Print varAttributes2(iatType).textString
        'End If
    End If

Next iatType
    TblPT(1) = TblPT(1) - nJumpHead
    For i = 1 To rcFix
        ' xHDWRSETID = !HDWRSETID
        Set blockRefObj = ThisDrawing.ModelSpace.InsertBlock _
                     (TblPT, nRowDwg, 1, 1, 1, 0)
        Dim varAttributes As Variant
        varAttributes = blockRefObj.GetAttributes
    '***************************************************************
If !FXIMGNAME <> "" Then
If ShowImage = True Then
    Dim imgPT(0 To 2) As Double
    Dim scalefactor, xSF As Double
    Dim rotAngleInDegree As Double, rotAngle As Double
    'Dim imageName As String
    Dim imageName As String

    Dim raster As AcadRasterImage
    Dim imgheight As Variant
    Dim imgwidth As Variant

    'imageName = "C:\AutoCAD\sample\downtown.jpg"
    imageName = !FXIMGNAME
    Debug.Print imageName
    'insertionPoint(0) = 2#: insertionPoint(1) = 2#: insertionPoint(2) = 0#
    imgPT(0) = TblPT(0) + 36: imgPT(1) = TblPT(1) - 54: imgPT(2) = TblPT(2)
    scalefactor = 48#
    'rotAngleInDegree = 0#
    'rotAngle = rotAngleInDegree * 3.141592 / 180#
    rotAngle = 0#
    
    
    
    ' Creates a raster image in model space
    'If !fximgname <> "" Then
        Set raster = ThisDrawing.ModelSpace.AddRaster(imageName, imgPT, scalefactor, rotAngle)
        With raster
        imgheight = raster.ImageHeight
        imgwidth = raster.ImageWidth
            If imgheight > 48 Then
                xSF = (48 / imgheight) * 48
                Debug.Print "xSF: " & xSF * 48
                 raster.scalefactor = xSF
            End If
        End With
    End If
End If
    '***************************************************************
        For iatFix = LBound(varAttributes) To UBound(varAttributes)
        
        Debug.Print varAttributes(iatFix).TagString
            If varAttributes(iatFix).TagString = "XKEY" Then 'XKEY
                If IsNull(![PFXNO]) = True Then
                    varAttributes(iatFix).textString = ""
                Else
                    varAttributes(iatFix).textString = ![PFXNO]
                    Debug.Print varAttributes(iatFix).textString
                End If
            End If
            If varAttributes(iatFix).TagString = "XMODEL1" Then 'XMODEL1
                If IsNull(SEPTEXT2(!FXMODEL, 1, 2, 16)) = True Then
                    varAttributes(iatFix).textString = ""
                Else
                    varAttributes(iatFix).textString = SEPTEXT2(!FXMODEL, 1, 2, 16)
                    Debug.Print varAttributes(iatFix).textString
                End If
            End If
            If varAttributes(iatFix).TagString = "XMODEL2" Then 'XMODEL2
                If IsNull(SEPTEXT2(!FXMODEL, 2, 2, 16)) = True Then
                    varAttributes(iatFix).textString = ""
                Else
                    varAttributes(iatFix).textString = SEPTEXT2(!FXMODEL, 2, 2, 16)
                    Debug.Print varAttributes(iatFix).textString
                End If
            End If
            If varAttributes(iatFix).TagString = "XNAME" Then 'XNAME
                If IsNull(!FXCAT) = True Then
                    varAttributes(iatFix).textString = ""
                Else
                    varAttributes(iatFix).textString = !FXCAT
                    Debug.Print varAttributes(iatFix).textString
                End If
            End If
            If varAttributes(iatFix).TagString = "'XCAT" Then 'XCAT
                If IsNull(!FXCAT) = True Then
                    varAttributes(iatFix).textString = ""
                Else
                    varAttributes(iatFix).textString = !FXCAT
                    Debug.Print varAttributes(iatFix).textString
                End If
            End If
            If varAttributes(iatFix).TagString = "XFIN" Then 'XFIN
                If IsNull(!FXCOLOR) = True Then
                    varAttributes(iatFix).textString = ""
                Else
                    varAttributes(iatFix).textString = !FXCOLOR
                    Debug.Print varAttributes(iatFix).textString
                End If
            End If
            If varAttributes(iatFix).TagString = "XMCOMP" Then 'XMCOMP
                If IsNull(![CONTACT_1.COMPANY]) = True Then
                    varAttributes(iatFix).textString = ""
                Else
                    varAttributes(iatFix).textString = ![CONTACT_1.COMPANY]
                    Debug.Print varAttributes(iatFix).textString
                End If
            End If
            If varAttributes(iatFix).TagString = "XMSTREET" Then 'XMSTREET
                If IsNull(![CONTACT_1.STREET]) = True Then
                    varAttributes(iatFix).textString = ""
                Else
                    varAttributes(iatFix).textString = ![CONTACT_1.STREET]
                    Debug.Print varAttributes(iatFix).textString
                End If
            End If
            If varAttributes(iatFix).TagString = "XMCSZ" Then 'XMCSZ
                If !MCSZ = "," Then
                    varAttributes(iatFix).textString = ""
                Else
                    varAttributes(iatFix).textString = !MCSZ
                    Debug.Print varAttributes(iatFix).textString
                End If
            End If
            If varAttributes(iatFix).TagString = "XMTEL" Then 'XMTEL
                If IsNull(![CONTACT_1.TEL_BUS]) = True Then
                    varAttributes(iatFix).textString = ""
                Else
                    varAttributes(iatFix).textString = Format(![CONTACT_1.TEL_BUS], "###-###-####")
                    Debug.Print varAttributes(iatFix).textString
                End If
            End If
            If varAttributes(iatFix).TagString = "XSCOMP" Then 'XSCOMP
                If IsNull(![CONTACT.COMPANY]) = True Then
                    varAttributes(iatFix).textString = ""
                Else
                    varAttributes(iatFix).textString = ![CONTACT.COMPANY]
                    Debug.Print varAttributes(iatFix).textString
                End If
            End If
            If varAttributes(iatFix).TagString = "XSSTREET" Then 'XSSTREET
                If IsNull(![CONTACT.STREET]) = True Then
                    varAttributes(iatFix).textString = ""
                Else
                    varAttributes(iatFix).textString = ![CONTACT.STREET]
                    Debug.Print varAttributes(iatFix).textString
                End If
            End If
            If varAttributes(iatFix).TagString = "XSCSZ" Then 'XSCSZ
                If !SCSZ = "," Then
                    varAttributes(iatFix).textString = ""
                Else
                    varAttributes(iatFix).textString = !SCSZ
                    Debug.Print varAttributes(iatFix).textString
                End If
            End If
            If varAttributes(iatFix).TagString = "XSTEL" Then 'XSTEL
                If IsNull(![CONTACT.TEL_BUS]) = True Then
                    varAttributes(iatFix).textString = ""
                Else
                    varAttributes(iatFix).textString = Format(![CONTACT.TEL_BUS], "###-###-####")
                    Debug.Print varAttributes(iatFix).textString
                End If
            End If
            If varAttributes(iatFix).TagString = "XNOTE1" Then 'XNOTE1 FXPRNOTE
                If IsNull(!FXPRNOTE) = True Then
                    varAttributes(iatFix).textString = ""
                Else
                    varAttributes(iatFix).textString = SEPTEXT2(!FXPRNOTE, 1, 3, 16)
                    Debug.Print varAttributes(iatFix).textString
                End If
            End If
            If varAttributes(iatFix).TagString = "XNOTE2" Then 'XNOTE2
                If IsNull(!FXPRNOTE) = True Then
                    varAttributes(iatFix).textString = ""
                Else
                    varAttributes(iatFix).textString = SEPTEXT2(!FXPRNOTE, 2, 3, 16)
                    Debug.Print varAttributes(iatFix).textString
                End If
            End If
            If varAttributes(iatFix).TagString = "XNOTE3" Then 'XNOTE3
                If IsNull(!FXPRNOTE) = True Then
                    varAttributes(iatFix).textString = ""
                Else
                    varAttributes(iatFix).textString = SEPTEXT2(!FXPRNOTE, 3, 3, 16)
                    Debug.Print varAttributes(iatFix).textString
                End If
            End If
            If varAttributes(iatFix).TagString = "XBUBTYPE" Then 'XBUBTYPE
                If IsNull(!BUBTYPE) = True Then
                    varAttributes(iatFix).textString = ""
                Else
                    varAttributes(iatFix).textString = !BUBTYPE
                    Debug.Print varAttributes(iatFix).textString
                End If
            End If
            If varAttributes(iatFix).TagString = "XBUBCAT" Then 'XBUBCAT
                If IsNull(!BUBCAT) = True Then
                    varAttributes(iatFix).textString = ""
                Else
                    varAttributes(iatFix).textString = !BUBCAT
                    Debug.Print varAttributes(iatFix).textString
                End If
            End If

            'Dim selectionSet1 As AcadSelectionSet
            'Set selectionSet1 = ThisDrawing.SelectionSets. _
                        Add("NewSelectionSet")

            'ssImg = ThisDrawing.SelectionSets.Item("ImgSet").Add
            'Set rasterObj.Name = ""
            'rasterObj = ThisDrawing.modelspace.ObjectName "cadimg"
            'Set rasterObj.ImageFile = !FXIMGNAME
            
        Next iatFix
        TblPT(1) = TblPT(1) - nJumpRow
        .MoveNext
    Next i
End With

frmSched_CSI.Hide


End Sub
Private Sub CommandButton3_Click()
FIXTURE
End Sub

Private Sub CommandButton4_Click()
LIGHT
End Sub







Sub zbackup_image()
    '***************************************************************
        Dim ssImg As AcadSelectionSet
        Dim ftype(0) As Integer
        Dim fdata(0) As Variant
        Dim dxfcode As Variant
        Dim dxfdata As Variant
        Dim rasterObj As AcadRasterImage
        
        ftype(0) = 1: fdata(0) = "IMAGE" ' type 0 = object type, 2 = name
        dxfcode = ftype(0)
        dxfdata = fdata(0)

        
        
        For Each ssImg In ThisDrawing.SelectionSets
        If ssImg.Name = "IMAGESET" Then
        Exit For
        End If
        Next ssImg
        
        If ssImg Is Nothing Then
        Set ssImg = ThisDrawing.SelectionSets.Add("IMAGESET")
        Else
        ssImg.Clear
        End If
        
        ssImg.Select acSelectionSetAll, , , dxfcode, dxfdata
'Set obj = ThisDrawing.ModelSpace.GetObject("Cadimg")
        If ssImg.Count > 0 Then
        
            'Dim oEntity As AcadEntity
            'Dim objImage As AcadRasterImage
            Dim imgEntity As AcadEntity
            'Dim rasterObj As AcadRasterImage
            
            For Each imgEntity In ssImg
            Set rasterObj = imgEntity
            If (rasterObj.Transparency) Then
            'MsgBox "yeah"
            rasterObj.Transparency = False
            Else
            rasterObj.Transparency = True
            End If
            'rasterObj.ImageFile = !fximgname
            Next
            Else
            MsgBox "No images inserted."
            'ThisDrawing.ModelSpace.rasterObj.ImageFile = !FXIMGNAME
            'Debug.Print ssImg.Item(1).Name
        End If
        
        'ThisDrawing.Regen True
        ssImg.Delete
        Set ssImg = Nothing
        
        
        
    '***************************************************************

End Sub

Attribute VB_Name = "frmSpec"
Attribute VB_Base = "0{433F3B41-49ED-48DD-8BD7-D045C7BBC3F5}{D499CF3C-9933-4E07-A0AB-2F16F737B019}"
Attribute VB_GlobalNameSpace = False
Attribute VB_Creatable = False
Attribute VB_PredeclaredId = True
Attribute VB_Exposed = False
Attribute VB_TemplateDerived = False
Attribute VB_Customizable = False

Public wksObj As Workspace
Public DB As Database
Public dbsObj As Database
Public tblObj As TableDef
Public fldObj As Field
Public rstObj, rstProj As Recordset


Private Sub CommandButton1_Click() ' TEST
Dim x As Integer

x = ListBox1
y = printspec(x)
End Sub

Public Sub CommandButton4_Click() 'Test Populate CSI
Dim RsPCSI2 As Recordset
Dim strPCSI2 As String
Dim DB As Database
Dim rn As Integer
Dim rcArray As Variant
ListBox1.Clear
'Set DB = OpenDatabase("h:\db\db_misc\JSPEC0310.mdb")
'Set DB = OpenDatabase("h:\db\db_misc\02_Jspec_B_001.mdb")
'Set DB = OpenDatabase("X:\db_misc\02_Jspec_B_001.mdb")
Set DB = OpenDatabase("\\jwja-svr-10\jdb\db_SPEC\X_JSPEC_17_01.mdb")
strPCSI2 = "SELECT PROJCSI.projcsiid, PROJCSI.PROJ_NO, MCSI.MCSI, MCSI.MCSINAME " _
& "FROM MCSI INNER JOIN PROJCSI ON MCSI.MCSIID = PROJCSI.MCSIID " _
& "WHERE (((PROJCSI.PROJ_NO) = '" & seleproj & "'))" _
& "ORDER BY MCSI.MCSI"
Set RsPCSI2 = DB.OpenRecordset(strPCSI2)
Debug.Print rn
Do Until RsPCSI2.EOF = True
    ListBox1.AddItem RsPCSI2!PROJCSIID
    ListBox1.List(ListBox1.ListCount - 1, 1) = RsPCSI2!mCSI
    ListBox1.List(ListBox1.ListCount - 1, 2) = RsPCSI2!MCSIname
    RsPCSI2.MoveNext
Loop
End Sub

Private Sub CommandButton5_Click() ' INSERT TEXT
Dim returnPnt As Variant
Dim width As Double
Dim text As String
Debug.Print ListBox1
 UserForm1.Hide
returnPnt = ThisDrawing.Utility.GetPoint(, "Enter a point: ")

    'corner(0) = 0#: corner(1) = 10#: corner(2) = 0#
    width = 10
    text = TextBox1
    ' Creates the mtext Object
    Set mtextObj = ThisDrawing.ModelSpace.AddMText(returnPnt, width, text)
    'ZoomAll
    ThisDrawing.Regen acActiveViewport
    UserForm1.Hide
End Sub


'**********************************************************************************************************
'**********************************************************************************************************
'
'12/22/17
'
'**********************************************************************************************************
'**********************************************************************************************************

Private Sub CommandButton6_Click() 'WRIET MTEXT
Dim x As Integer
If IsNull(ListBox1) = True Then
    MsgBox "Must select a CSI from the list!"
    Exit Sub
Else
    x = ListBox1
    y = writemtext(x) '<<<<<<<<<<<<<<<<<<<<<<<<<<<<<<<<<<<<<<<<<<<<<<<<<<<<<<<<<
    frmSpec.Hide
End If

End Sub





Public Sub ListBox1_Click()
Dim RsPart As Recordset
Dim strPpart As String
Dim DB As Database
Dim rn As Integer
Dim rcArray As Variant

'**********************************************************************************************************
'**********************************************************************************************************

Set DB = OpenDatabase("\\jwja-svr-10\jdb\db_SPEC\X_JSPEC_17_01.mdb")
'Set DB = OpenDatabase("H:\db\db_misc\JSPEC04_01.mdb")
'Set DB = OpenDatabase("X:\db_misc\02_Jspec_B_001.mdb")
'Set DB = OpenDatabase("h:\db\db_misc\02_Jspec_B_001.mdb")
'Set DB = OpenDatabase("h:\db\db_misc\JSPEC0310.mdb")

'**********************************************************************************************************
'**********************************************************************************************************

strPpart = "SELECT PROJPART.PROJCSIID, PROJPART.MPARTID, PROJPART.PROJPARTNO, MPART.MPART " _
& "FROM PROJPART INNER JOIN MPART ON PROJPART.MPARTID = MPART.MPARTID " _
& "WHERE (((PROJPART.PROJCSIID)=" & ListBox1 & "));"
Set RsPart = DB.OpenRecordset(strPpart)
Debug.Print RsPart.RecordCount

ListBox2.Clear

Do Until RsPart.EOF = True
    ListBox2.AddItem RsPart!MPARTID
    ListBox2.List(ListBox2.ListCount - 1, 1) = RsPart!MPART

    RsPart.MoveNext
Loop
'RsPart.Close

End Sub
Sub selectpt()
Dim returnPnt As Variant
Dim width As Double
Dim text As String
Debug.Print ListBox1
returnPnt = ThisDrawing.Utility.GetPoint(, "Enter a point: ")

    'corner(0) = 0#: corner(1) = 10#: corner(2) = 0#
    width = 10
    text = ListBox1
    ' Creates the mtext Object
    Set mtextObj = ThisDrawing.ModelSpace.AddMText(returnPnt, width, text)
    ZoomAll
ThisDrawing.Regen acActiveViewport
End Sub


'ZZZZZZZZZZZZZZZZZZZZZZZZZZZZZZZZZZZZZZZZZZZZZZZZZZZZZZZZZZZZZZZZZZZZZZZZZZZZZZZZZZZZZZZZZZZZZZZZZZZZZZZZZZ
'ZZZZZZZZZZZZZZZZZZZZZZZZZZZZZZZZZZZZZZZZZZZZZZZZZZZZZZZZZZZZZZZZZZZZZZZZZZZZZZZZZZZZZZZZZZZZZZZZZZZZZZZZZZ
'
'12/22/17 NOT NEEDED
'
'ZZZZZZZZZZZZZZZZZZZZZZZZZZZZZZZZZZZZZZZZZZZZZZZZZZZZZZZZZZZZZZZZZZZZZZZZZZZZZZZZZZZZZZZZZZZZZZZZZZZZZZZZZZ
'ZZZZZZZZZZZZZZZZZZZZZZZZZZZZZZZZZZZZZZZZZZZZZZZZZZZZZZZZZZZZZZZZZZZZZZZZZZZZZZZZZZZZZZZZZZZZZZZZZZZZZZZZZZ

Sub opendb()
Dim WS As Workspace
Dim DB As Database
Dim rs As Recordset
Dim strPCSI As String

'Define the workgroup information file (system database) you will use.

'DBEngine.SystemDB = "H:\DB\DB_MISC\SECURITY.mdw"
'DBEngine.SystemDB = "C:\Documents and Settings\Jinwoo\Application Data\Microsoft\Access\System6.mdw"
'DBEngine.SystemDB = "C:\Documents and Settings\jwjang\Application Data\Microsoft\Access\System.mdw"
'DBEngine.SystemDB = "h:\DB\JW0610.mdw"
DBEngine.SystemDB = "\\jwja-svr-10\jdb\DB\JW0610.mdw"

'OPTIONAL: Create a workspace with the correct login information
'Set WS = CreateWorkspace("NewWS", "MyID", "MyPwd", dbUseJet)
'OPTIONAL: If you set the workspace object, you can use the new
'workspace with the OpenDatabase command. For example:

'Set Db = WS.OpenDatabase("C:\My Documents\MyDB.mdb")
Set DB = OpenDatabase("\\jwja-svr-10\jdb\db_SPEC\X_JSPEC_17_01.mdb")
'Set DB = OpenDatabase("H:\db\db_SPEC\H_H_JSPEC04_02.mdb")
'Set DB = OpenDatabase("X:\db_misc\02_Jspec_B_001.mdb")
'Set DB = OpenDatabase("h:\db\db_misc\02_Jspec_B_001.mdb")
'Set DB = OpenDatabase("h:\db\db_misc\JSPEC0310.mdb")
'Set Rs = DB.OpenRecordset("project")

strPCSI = "SELECT PROJSPEC.PROJSPECID, PROJSPEC.PROJ_NO, PROJSPEC.NOTE, " _
 & "PROJSPEC.PROJSPECDATE, PROJSPEC.NOTE, Project.PROJ_NAME " _
 & "FROM PROJSPEC INNER JOIN Project ON PROJSPEC.PROJ_NO = Project.PROJ_NO " _
 & "ORDER BY PROJSPEC.PROJSPECID DESC"
 
Set rs = DB.OpenRecordset(strPCSI)
Do Until rs.EOF = True
    seleproj.AddItem rs!PROJ_NO
    rs.MoveNext
Loop
rs.Close
Set rs = Nothing
DB.Close
Set DB = Nothing
'OPTIONAL: If you set the WS object, use the following to clean up
'WS.Close
'Set WS = Nothing
MsgBox "Done"
End Sub
'ZZZZZZZZZZZZZZZZZZZZZZZZZZZZZZZZZZZZZZZZZZZZZZZZZZZZZZZZZZZZZZZZZZZZZZZZZZZZZZZZZZZZZZZZZZZZZZZZZZZZZZZZZZ
'ZZZZZZZZZZZZZZZZZZZZZZZZZZZZZZZZZZZZZZZZZZZZZZZZZZZZZZZZZZZZZZZZZZZZZZZZZZZZZZZZZZZZZZZZZZZZZZZZZZZZZZZZZZ
'ZZZZZZZZZZZZZZZZZZZZZZZZZZZZZZZZZZZZZZZZZZZZZZZZZZZZZZZZZZZZZZZZZZZZZZZZZZZZZZZZZZZZZZZZZZZZZZZZZZZZZZZZZZ
'ZZZZZZZZZZZZZZZZZZZZZZZZZZZZZZZZZZZZZZZZZZZZZZZZZZZZZZZZZZZZZZZZZZZZZZZZZZZZZZZZZZZZZZZZZZZZZZZZZZZZZZZZZZ

'**********************************************************************************************************
'**********************************************************************************************************
'
'12/22/17
'
'**********************************************************************************************************
'**********************************************************************************************************

Private Sub ListBox2_Click()
Dim RsPart As Recordset
Dim strPpart As String
Dim DB As Database
Dim rn As Integer
Dim rcArray As Variant

'**********************************************************************************************************
'**********************************************************************************************************
Set DB = OpenDatabase("\\jwja-svr-10\jdb\db_SPEC\X_JSPEC_17_01.mdb")
'Set DB = OpenDatabase("X:\db_misc\02_Jspec_B_001.mdb")
'Set DB = OpenDatabase("h:\db\db_misc\JSPEC0310.mdb")
'**********************************************************************************************************
'**********************************************************************************************************

strPpart = "SELECT PROJPART.PROJCSIID, PROJPART.MPARTID, PROJPART.PROJPARTNO, MPART.MPART " _
& "FROM PROJPART INNER JOIN MPART ON PROJPART.MPARTID = MPART.MPARTID " _
& "WHERE (((PROJPART.PROJCSIID)=" & ListBox1 & "));"
Set RsPart = DB.OpenRecordset(strPpart)
Debug.Print RsPart.RecordCount

'TextBox1.Clear

Do Until RsPart.EOF = True
    TextBox1 = RsPart!MPART
    RsPart.MoveNext
Loop
RsPart.Close

End Sub

Private Sub seleproj_Change()
frmSpec.Repaint
CommandButton4_Click 'POPULATE CSI

End Sub

'**********************************************************************************************************
'**********************************************************************************************************
'
'12/22/17
'
'**********************************************************************************************************
'**********************************************************************************************************


Public Sub UserForm_Initialize()
'Dim WS As Workspace
Dim DB As Database
Dim RsPCSI As Recordset
Dim strPCSI As String

' Define the workgroup information file (system database) you will use.
'DBEngine.SystemDB = "C:\Documents and Settings\Jinwoo\Application Data\Microsoft\Access\System6.mdw"
'DBEngine.SystemDB = "C:\Documents and Settings\jwjang\Application Data\Microsoft\Access\system.mdw"
DBEngine.SystemDB = "\\jwja-svr-10\jdb\JW0610.mdw"
' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")

'**********************************************************************************************************
'**********************************************************************************************************
'**********************************************************************************************************
'**********************************************************************************************************

Set DB = OpenDatabase("\\jwja-svr-10\jdb\db_SPEC\X_JSPEC_17_01.mdb")
'Set DB = OpenDatabase("H:\db\db_misc\JSPEC04_01.mdb")
'Set DB = OpenDatabase("X:\db_misc\02_Jspec_B_001.mdb")
'Set DB = OpenDatabase("h:\db\db_misc\JSPEC0310.mdb")

'**********************************************************************************************************
'**********************************************************************************************************
'**********************************************************************************************************

'Set Rs = DB.OpenRecordset("project")

strPCSI = "SELECT PROJSPEC.PROJSPECID, PROJSPEC.PROJ_NO, PROJSPEC.NOTE, " _
& "PROJSPEC.PROJSPECDATE, PROJSPEC.NOTE, Project.PROJ_NAME " _
& "FROM PROJSPEC INNER JOIN Project ON PROJSPEC.PROJ_NO = Project.PROJ_NO " _
& "ORDER BY PROJSPEC.PROJ_NO desc"
Set RsPCSI = DB.OpenRecordset(strPCSI)

Do Until RsPCSI.EOF = True
    seleproj.AddItem RsPCSI!PROJ_NO
    seleproj.List(seleproj.ListCount - 1, 1) = RsPCSI!PROJ_NAME
    RsPCSI.MoveNext
Loop
RsPCSI.Close
Set RsPCSI = Nothing
DB.Close
Set DB = Nothing

' OPTIONAL: If you set the WS object, use the following to clean up
'WS.Close
'Set WS = Nothing

MsgBox "LOADED!"

End Sub



Sub ComboBox1_afterupdate()
strPCSI2 = "SELECT PROJCSI.PROJ_NO, MCSI.MCSI, MCSI.MCSINAME " _
& "FROM MCSI INNER JOIN PROJCSI ON MCSI.MCSIID = PROJCSI.MCSIID " _
& " ON PROJSPEC.PROJ_NO = Project.PROJ_NO" _
 & "WHERE (((PROJCSI.PROJ_NO) = " & seleproj & ")) " _
 & "ORDER BY MCSI.MCSI"
Set RsPCSI2 = DB.OpenRecordset(strPCSI2)

Do Until RsPCSI2.EOF = True
    ListBox1.AddItem RsPCSI2!PROJ_NO
    RsPCSI2.MoveNext
Loop
End Sub



Private Sub CommandButton2_Click()
 On Error Resume Next
   
    Set dbsObj = DBEngine.Workspaces(0).OpenDatabase("\\jwja-svr-10\jdb\db_SPEC\X_JSPEC_17_01.mdb")
  
   'Set dbsObj = DBEngine.Workspaces(0).OpenDatabase("X:\db_misc\02_Jspec_B_001.mdb")
      'Set dbsObj = DBEngine.Workspaces(0).OpenDatabase("h:\db\db_misc\JSPEC0310.mdb")

   Set rstProj = dbsObj.OpenRecordset("project", dbOpenDynaset)

   strPCSI = "SELECT PROJSPEC.PROJSPECID, PROJSPEC.PROJ_NO, PROJSPEC.NOTE, " _
    & "PROJSPEC.PROJSPECDATE, PROJSPEC.NOTE, Project.PROJ_NAME " _
    & "FROM PROJSPEC INNER JOIN Project ON PROJSPEC.PROJ_NO = Project.PROJ_NO"
    Set rstPCSI = dbsObj.OpenRecordset(strPCSI)

   Set dbsObj = Nothing
End Sub

Private Sub CommandButton3_Click() 'QUIT
Unload Me
End Sub

Attribute VB_Name = "frmWallType"
Attribute VB_Base = "0{7CC8819E-0A05-42BD-8455-62B9F45F2511}{7B57BF89-3E0E-41DE-9E48-D98E46FF3A7D}"
Attribute VB_GlobalNameSpace = False
Attribute VB_Creatable = False
Attribute VB_PredeclaredId = True
Attribute VB_Exposed = False
Attribute VB_TemplateDerived = False
Attribute VB_Customizable = False








'==========================================================================================================
' 9/21/18
'==========================================================================================================
Public Sub UserForm_Initialize()
'Dim WS As Workspace
Dim DB As Database
Dim rstSeleProj As Recordset
Dim strSeleProj As String

' Define the workgroup information file (system database) you will use.
'DBEngine.SystemDB = "C:\Documents and Settings\Jinwoo\Application Data\Microsoft\Access\System6.mdw"
'DBEngine.SystemDB = "C:\Documents and Settings\jwjang\Application Data\Microsoft\Access\system.mdw"
DBEngine.SystemDB = "\\jwja-svr-10\jdb\JW0610.mdw"
' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")

'**********************************************************************************************************
'**********************************************************************************************************
'**********************************************************************************************************
'**********************************************************************************************************

Set DB = OpenDatabase("\\jwja-svr-10\jdb\DB_WALL\WALLASS03.mdb")
'Set DB = OpenDatabase("H:\db\db_misc\JSPEC04_01.mdb")
'Set DB = OpenDatabase("X:\db_misc\02_Jspec_B_001.mdb")
'Set DB = OpenDatabase("h:\db\db_misc\JSPEC0310.mdb")

'**********************************************************************************************************
'**********************************************************************************************************
'**********************************************************************************************************

'Set Rs = DB.OpenRecordset("project")

strSeleProj = "SELECT ProjBldgEnv.ProjBldgEnvID, ProjBldgEnv.Proj_no, Project.PROJ_NAME " _
& "FROM Project INNER JOIN ProjBldgEnv ON Project.PROJ_NO = ProjBldgEnv.Proj_no " _
& "ORDER BY ProjBldgEnv.proj_no DESC"

Set rstSeleProj = DB.OpenRecordset(strSeleProj)

Do Until rstSeleProj.EOF = True

    seleproj.AddItem rstSeleProj!ProjBldgEnvid
    
    seleproj.List(seleproj.ListCount - 1, 1) = rstSeleProj!PROJ_NO
    seleproj.List(seleproj.ListCount - 1, 2) = rstSeleProj!PROJ_NAME
    rstSeleProj.MoveNext
Loop
rstSeleProj.Close



Set rstSeleProj = Nothing
DB.Close
Set DB = Nothing

' OPTIONAL: If you set the WS object, use the following to clean up
'WS.Close
'Set WS = Nothing

MsgBox "LOADED!"
End Sub

Private Sub seleproj_Change()
'==========================================================================================================
' 9/21/18
'==========================================================================================================

Me.Repaint
Dim DB As Database
Dim rstProjBldgEnvItem  As Recordset
Dim strProjBldgEnvItem  As String
Dim rn As Integer

DBEngine.SystemDB = "\\jwja-svr-10\jdb\JW0610.mdw"
Set DB = OpenDatabase("\\jwja-svr-10\jdb\DB_WALL\WALLASS03.mdb")
'=============================================================================================================
' Show all ProjBldgEnv
'=============================================================================================================
strProjBldgEnvItem = "SELECT ProjBldgEnv.Proj_no, ProjBldgEnv.ProjBldgEnvID, ProjBldgEnv.ProjBldgEnvName " _
& "FROM ProjBldgEnv " _
& "WHERE (((ProjBldgEnv.ProjBldgEnvID)=" & seleproj & "))"
'=============================================================================================================
'=============================================================================================================


Me.lsProjBldgEnv.Clear
Set rstProjBldgEnvItem = DB.OpenRecordset(strProjBldgEnvItem)
'Debug.Print rn
Do Until rstProjBldgEnvItem.EOF = True
    lsProjBldgEnv.AddItem rstProjBldgEnvItem!ProjBldgEnvid
    'istseleCode.List(listseleCode.ListCount - 1, 1) = rstProjCodeItem!vCahpterNo
    lsProjBldgEnv.List(lsProjBldgEnv.ListCount - 1, 1) = rstProjBldgEnvItem!ProjBldgEnvName
    rstProjBldgEnvItem.MoveNext
Loop

rstProjBldgEnvItem.Close

Set rstProjBldgEnvItem = Nothing

DB.Close
Set DB = Nothing
End Sub

Private Sub lsProjBldgEnv_Click()
Me.Repaint
Dim DB As Database
Dim rstProjEnvItem As Recordset
Dim strProjEnvItem As String
Dim rn As Integer

DBEngine.SystemDB = "\\jwja-svr-10\jdb\JW0610.mdw"
Set DB = OpenDatabase("\\jwja-svr-10\jdb\DB_WALL\WALLASS03.mdb")

'=============================================================================================================
'=============================================================================================================
' Show ProjEnvItems
'=============================================================================================================
'
strProjEnvItem = "SELECT ConnProjBldgEnv.ProjBldgEnvid, ConnProjBldgEnv.ProjENvID, ProjEnvItem.ProjEnvNo, " _
& "ProjEnvItem.ProjENvCategory, ProjEnvItem.ProjEnvType, ProjEnvItem.ProjENvName " _
& "FROM ProjEnvItem INNER JOIN ConnProjBldgEnv ON ProjEnvItem.ProjEnvID = ConnProjBldgEnv.ProjENvID " _
& "WHERE (((ConnProjBldgEnv.ProjBldgEnvid)=" & lsProjBldgEnv & "));"
Me.lsEnvItem.Clear
Set rstProjEnvItem = DB.OpenRecordset(strProjEnvItem)

Do Until rstProjEnvItem.EOF = True
    lsEnvItem.AddItem rstProjEnvItem!ProjEnvID
    'istseleCode.List(listseleCode.ListCount - 1, 1) = rstProjCodeItem!vCahpterNo
    If IsNull(rstProjEnvItem!ProjEnvName) = False Then
    
    lsEnvItem.List(lsEnvItem.ListCount - 1, 1) = rstProjEnvItem!ProjEnvName
    Else
    lsEnvItem.List(lsEnvItem.ListCount - 1, 1) = ""
    End If
    rstProjEnvItem.MoveNext
Loop
rstProjEnvItem.Close
Set rstProjEnvItem = Nothing
DB.Close
Set DB = Nothing

End Sub
Private Sub cmdWritheWallType_Click()
Dim x, y, mProjBldgEnvID As Integer
If IsNull(lsProjBldgEnv) = True Then
    MsgBox "Must select a Proj Bldg Env Item from the list!"
    Exit Sub
Else
    'x = lsProjBldgEnv
    mProjBldgEnvID = lsProjBldgEnv
    y = writeProjENV(mProjBldgEnvID) '<<<<<<<<<<<<<<<<<<<<<<<<<<<<<<<<<<<<<<<<<<<<<<<<<<<<<<<<<
    frmWallType.Hide
End If
End Sub

Attribute VB_Name = "frmWorkItem"
Attribute VB_Base = "0{A5591954-47C2-4BD4-9382-421CC8BB0D65}{156237B4-A07C-4812-850A-A1ECC4929083}"
Attribute VB_GlobalNameSpace = False
Attribute VB_Creatable = False
Attribute VB_PredeclaredId = True
Attribute VB_Exposed = False
Attribute VB_TemplateDerived = False
Attribute VB_Customizable = False

Public wksObj As Workspace
Public DB As Database
Public dbsObj As Database
Public tblObj As TableDef
Public fldObj As Field
Public rstObj, rstProj As Recordset



Private Sub CheckBox1_Click()

End Sub

Private Sub CommandButton3_Click()
Unload Me
End Sub

Private Sub CommandButton7_Click()
Dim x As Integer
'If IsNull(ListBox1) = True Then
'If ListBox1.Selected(1) = False Then
'MsgBox "Must select a Assembly Item from the list!"
'Exit Sub
'Else
'x = ListBox1
If mCad = False Then
writeAssWorkItemImg 'DEFAULT
Else
writeAssWorkItemImgCAD
End If
'frmWorkItem.HIDE
'End If

End Sub




Private Sub mCategory_Click()
CommandButton4_Click
End Sub

Public Sub UserForm_Initialize()
'Dim WS As Workspace
Dim DB As Database
Dim rstProj As Recordset
Dim strProj As String

' Define the workgroup information file (system database) you will use.
'DBEngine.SystemDB = "C:\Documents and Settings\Jinwoo\Application Data\Microsoft\Access\System6.mdw"
'DBEngine.SystemDB = "C:\Documents and Settings\jwjang\Application Data\Microsoft\Access\system.mdw"

'DCHANGE

'DBEngine.SystemDB = "H:\DB\JW0610.mdw"
DBEngine.SystemDB = "\\jwja-svr-10\jdb\JW0610.mdw"
' OPTIONAL: Create a workspace with the correct login information
'Set WS = CreateWorkspace("NewWS", "MyID", "MyPwd", dbUseJet)
' OPTIONAL: If you set the workspace object, you can use the new
'           workspace with the OpenDatabase command. For example:
'Set Db = WS.OpenDatabase("C:\My Documents\MyDB.mdb")
'
'Set DB = OpenDatabase("H:\db\db_est\H_H_EST_2013_001.mdb")
Set DB = OpenDatabase("\\jwja-svr-10\jdb\db_est\x_EST_2013_001.mdb")

'Set DB = OpenDatabase("X:\db_misc\02_Jspec_B_001.mdb")
'Set DB = OpenDatabase("h:\db\db_misc\JSPEC0310.mdb")

'Set Rs = DB.OpenRecordset("project")

'strPCSI = "SELECT PROJSPEC.PROJSPECID, PROJSPEC.PROJ_NO, PROJSPEC.NOTE, " _
& "PROJSPEC.PROJSPECDATE, PROJSPEC.NOTE, Project.PROJ_NAME " _
& "FROM PROJSPEC INNER JOIN Project ON PROJSPEC.PROJ_NO = Project.PROJ_NO " _
& "ORDER BY PROJSPEC.PROJ_NO"

strProj = "SELECT ASS.proj_no, Project.PROJ_NAME " _
& "FROM ASS INNER JOIN Project ON ASS.proj_no = Project.PROJ_NO " _
& "GROUP BY ASS.proj_no, Project.PROJ_NAME, Project.INPUT " _
& "ORDER BY Project.INPUT DESC"



Set rstProj = DB.OpenRecordset(strProj)

Do Until rstProj.EOF = True
    seleproj.AddItem rstProj!PROJ_NO
    seleproj.List(seleproj.ListCount - 1, 1) = rstProj!PROJ_NAME
    rstProj.MoveNext
Loop
rstProj.Close
Set rstProj = Nothing
DB.Close
Set DB = Nothing

' OPTIONAL: If you set the WS object, use the following to clean up
'WS.Close
'Set WS = Nothing

MsgBox "Project List for WorkItems LOADED!"

End Sub


Private Sub seleproj_Change()
'UserForm1.Repaint
CommandButton4_Click 'POPULATE CSI
End Sub
Public Sub CommandButton4_Click() 'Test Populate CSI
Dim rstProjAss As Recordset
Dim strProjAss As String
Dim DB As Database
Dim rn As Integer
Dim rcArray As Variant
ListBox1.Clear
ListBox1.MultiSelect = fmMultiSelectExtended
'Set DB = OpenDatabase("h:\db\db_misc\JSPEC0310.mdb")
'Set DB = OpenDatabase("h:\db\db_misc\02_Jspec_B_001.mdb")
'Set DB = OpenDatabase("X:\db_misc\02_Jspec_B_001.mdb")
'Set DB = OpenDatabase("H:\db\db_misc\JSPEC04_01.mdb")

'Set DB = OpenDatabase("H:\db\db_est\H_H_EST_2013_001.mdb")
Set DB = OpenDatabase("\\jwja-svr-10\jdb\db_est\x_EST_2013_001.mdb")

'strPCSI2 = "SELECT PROJCSI.projcsiid, PROJCSI.PROJ_NO, MCSI.MCSI, MCSI.MCSINAME " _
& "FROM MCSI INNER JOIN PROJCSI ON MCSI.MCSIID = PROJCSI.MCSIID " _
& "WHERE (((PROJCSI.PROJ_NO) = '" & seleproj & "'))" _
& "ORDER BY MCSI.MCSI"
If frmWorkItem.mCategory = True Then
strProjAss = "SELECT ASS.ASSID, ASS.ESTID, ASS.ASSDIV, ASS.ASSNO, ASS.ASSSUBDIV, ASS.ASSNAME, ASS.proj_no, " _
    & "ASS.CATEGORY_ID, CATEGORY.category_no, CATEGORY.category, CATEGORY.category_note " _
    & "FROM ASS INNER JOIN CATEGORY ON ASS.CATEGORY_ID=CATEGORY.category_id " _
& "WHERE (((ASS.proj_no) = '" & seleproj & "'))" _
& "ORDER BY CATEGORY.category_no"
Else
strProjAss = "SELECT ASS.ASSID, ASS.ESTID, ASS.ASSDIV, ASS.ASSNO, ASS.ASSSUBDIV, ASS.ASSNAME, ASS.proj_no " _
& "FROM ASS " _
& "WHERE (((ASS.proj_no) = '" & seleproj & "'))" _
& "ORDER BY ASS.ASSDIV, ASS.ASSNO"

End If

Set rstProjAss = DB.OpenRecordset(strProjAss)
Debug.Print rn
Do Until rstProjAss.EOF = True
    If frmWorkItem.mCategory = True Then
    ListBox1.AddItem rstProjAss!ASSID
    ListBox1.List(ListBox1.ListCount - 1, 1) = rstProjAss!category_id
    ListBox1.List(ListBox1.ListCount - 1, 2) = rstProjAss!category_no
    ListBox1.List(ListBox1.ListCount - 1, 3) = rstProjAss!category
    Else
    ListBox1.AddItem rstProjAss!ASSID
    ListBox1.List(ListBox1.ListCount - 1, 1) = rstProjAss!assdiv
    ListBox1.List(ListBox1.ListCount - 1, 2) = rstProjAss!assno
    ListBox1.List(ListBox1.ListCount - 1, 3) = rstProjAss!ASSNAME
    End If
    rstProjAss.MoveNext
Loop
rstProjAss.Close
Set rstProjAss = Nothing
DB.Close
Set DB = Nothing
End Sub
Private Sub ListBox1_Click()
Dim rstAssItem As Recordset
Dim strAssItem As String
Dim DB As Database
Dim rn As Integer
Dim rcArray As Variant
'Set DB = OpenDatabase("H:\db\db_est\H_H_EST_2013_001.mdb")
Set DB = OpenDatabase("\\jwja-svr-10\jdb\db_est\x_EST_2013_001.mdb")


'Set DB = OpenDatabase("H:\db\db_misc\JSPEC04_01.mdb")
'Set DB = OpenDatabase("X:\db_misc\02_Jspec_B_001.mdb")
'Set DB = OpenDatabase("h:\db\db_misc\02_Jspec_B_001.mdb")
'Set DB = OpenDatabase("h:\db\db_misc\JSPEC0310.mdb")
'strPpart = "SELECT PROJPART.PROJCSIID, PROJPART.MPARTID, PROJPART.PROJPARTNO, MPART.MPART " _
& "FROM PROJPART INNER JOIN MPART ON PROJPART.MPARTID = MPART.MPARTID " _
& "WHERE (((PROJPART.PROJCSIID)=" & ListBox1 & "));"

strAssItem = "SELECT WORK.ASSID, WORK.WKID, WORK.WKCSINO, WORK.WKCSINAME, WORK.WKNOTE " _
& "FROM ASS INNER JOIN [WORK] ON ASS.ASSID = WORK.ASSID " _
& "WHERE (((WORK.ASSID) =" & ListBox1 & "))" _
& "ORDER BY WORK.WKCSINO;"

Set rstAssItem = DB.OpenRecordset(strAssItem)
Debug.Print rstAssItem.RecordCount

ListBox2.Clear

Do Until rstAssItem.EOF = True
    ListBox2.AddItem rstAssItem!wkid
    ListBox2.List(ListBox2.ListCount - 1, 1) = rstAssItem!wkcsino

    rstAssItem.MoveNext
Loop
'RsPart.Close
rstAssItem.Close
Set rstAssItem = Nothing
DB.Close
Set DB = Nothing
End Sub

Private Sub CommandButton6_Click()
Dim x As Integer
'If IsNull(ListBox1) = True Then
'MsgBox "Must select a Assembly Item from the list!"
'Exit Sub
'Else
'x = ListBox1
writeWorkItemImg
'frmWorkItem.HIDE
'End If


End Sub
